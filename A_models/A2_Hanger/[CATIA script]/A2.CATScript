Language="VBSCRIPT"

Sub CATMain()

Dim documents1 As Documents
Set documents1 = CATIA.Documents
Dim productDocument1 As Document
Set productDocument1 = documents1.Add("Product")

Dim product1 As Product
Set product1 = productDocument1.Product

Dim products1 As Products
Set products1 = product1.Products

Dim arrayOfVariantOfBSTR1(0)
arrayOfVariantOfBSTR1(0) = ".\SubAssembly\Plate.CATPart"
products1.AddComponentsFromFiles arrayOfVariantOfBSTR1, "All"

Dim arrayOfVariantOfBSTR2(0)
arrayOfVariantOfBSTR2(0) = ".\SubAssembly\DM.CATPart"
products1.AddComponentsFromFiles arrayOfVariantOfBSTR2, "All"

Dim constraints1 As Collection
Set constraints1 = product1.Connections("CATIAConstraints")

Dim reference1 As Reference
Set reference1 = product1.CreateReferenceFromName("Product1/DM.1/!Axis:(Selection_RSur:(Face:(Brp:(Pocket.2;0:(Brp:(Sketch.3;6)));None:();Cf11:());Pocket.2_ResultOUT;Z0;G4162))")

Dim reference2 As Reference
Set reference2 = product1.CreateReferenceFromName("Product1/Plate.1/!Axis:(Selection_RSur:(Face:(Brp:(Pad.1;0:(Brp:(Sketch.1;21)));None:();Cf11:());Pad.1_ResultOUT;Z0;G4162))")

Dim constraint1 As Constraint
Set constraint1 = constraints1.AddBiEltCst(catCstTypeOn, reference1, reference2)

product1.Update 

Set constraints1 = product1.Connections("CATIAConstraints")

Dim reference3 As Reference
Set reference3 = product1.CreateReferenceFromName("Product1/Plate.1/!Axis:(Selection_RSur:(Face:(Brp:(Pad.1;0:(Brp:(Sketch.1;19)));None:();Cf11:());Pad.1_ResultOUT;Z0;G4162))")

Dim reference4 As Reference
Set reference4 = product1.CreateReferenceFromName("Product1/DM.1/!Selection_RSur:(Face:(Brp:(Pad.1;0:(Brp:(Sketch.1;8)));None:();Cf11:());Pocket.2_ResultOUT;Z0;G4162)")

Dim constraint2 As Constraint
Set constraint2 = constraints1.AddBiEltCst(catCstTypeOn, reference3, reference4)

Set productDocument1 = CATIA.ActiveDocument

Dim selection1 As Selection
Set selection1 = productDocument1.Selection

selection1.Clear 

selection1.Add constraint2

selection1.Delete 

Set productDocument1 = CATIA.ActiveDocument

Dim selection2 As Selection
Set selection2 = productDocument1.Selection

selection2.Clear 

selection2.Add constraint1

selection2.Delete 

Set productDocument1 = CATIA.ActiveDocument

Dim selection3 As Selection
Set selection3 = productDocument1.Selection

selection3.Clear 

Dim product2 As Product
Set product2 = products1.Item("DM.1")

selection3.Add product2

selection3.Delete 

Dim arrayOfVariantOfBSTR3(0)
arrayOfVariantOfBSTR3(0) = ".\SubAssembly\DM.CATPart"
products1.AddComponentsFromFiles arrayOfVariantOfBSTR3, "All"

Set constraints1 = product1.Connections("CATIAConstraints")

Dim reference5 As Reference
Set reference5 = product1.CreateReferenceFromName("Product1/DM.1/!Axis:(Selection_RSur:(Face:(Brp:(Pocket.2;0:(Brp:(Sketch.3;6)));None:();Cf11:());Pocket.2_ResultOUT;Z0;G4162))")

Set reference2 = product1.CreateReferenceFromName("Product1/Plate.1/!Axis:(Selection_RSur:(Face:(Brp:(Pad.1;0:(Brp:(Sketch.1;21)));None:();Cf11:());Pad.1_ResultOUT;Z0;G4162))")

Dim constraint3 As Constraint
Set constraint3 = constraints1.AddBiEltCst(catCstTypeOn, reference5, reference2)

Set constraints1 = product1.Connections("CATIAConstraints")

Dim reference6 As Reference
Set reference6 = product1.CreateReferenceFromName("Product1/DM.1/!Axis:(Selection_RSur:(Face:(Brp:(Pocket.2;0:(Brp:(Sketch.3;8)));None:();Cf11:());Pocket.2_ResultOUT;Z0;G4162))")

Set reference3 = product1.CreateReferenceFromName("Product1/Plate.1/!Axis:(Selection_RSur:(Face:(Brp:(Pad.1;0:(Brp:(Sketch.1;19)));None:();Cf11:());Pad.1_ResultOUT;Z0;G4162))")

Dim constraint4 As Constraint
Set constraint4 = constraints1.AddBiEltCst(catCstTypeOn, reference6, reference3)

Set constraints1 = product1.Connections("CATIAConstraints")

Dim reference7 As Reference
Set reference7 = product1.CreateReferenceFromName("Product1/DM.1/!Axis:(Selection_RSur:(Face:(Brp:(Pocket.2;0:(Brp:(Sketch.3;4)));None:();Cf11:());Pocket.2_ResultOUT;Z0;G4162))")

Dim reference8 As Reference
Set reference8 = product1.CreateReferenceFromName("Product1/Plate.1/!Axis:(Selection_RSur:(Face:(Brp:(Pad.1;0:(Brp:(Sketch.1;17)));None:();Cf11:());Pad.1_ResultOUT;Z0;G4162))")

Dim constraint5 As Constraint
Set constraint5 = constraints1.AddBiEltCst(catCstTypeOn, reference7, reference8)

Set constraints1 = product1.Connections("CATIAConstraints")

Dim reference9 As Reference
Set reference9 = product1.CreateReferenceFromName("Product1/DM.1/!Selection_RSur:(Face:(Brp:(Pad.1;0:(Brp:(Sketch.1;4)));None:();Cf11:());Pocket.2_ResultOUT;Z0;G4162)")

Dim reference10 As Reference
Set reference10 = product1.CreateReferenceFromName("Product1/Plate.1/!Selection_RSur:(Face:(Brp:(Pad.1;2);None:();Cf11:());Pad.1_ResultOUT;Z0;G4162)")

Dim constraint6 As Constraint
Set constraint6 = constraints1.AddBiEltCst(catCstTypeSurfContact, reference9, reference10)

product1.Update 

Dim arrayOfVariantOfBSTR4(0)
arrayOfVariantOfBSTR4(0) = ".\SubAssembly\DM.CATPart"
products1.AddComponentsFromFiles arrayOfVariantOfBSTR4, "All"

Set constraints1 = product1.Connections("CATIAConstraints")

Dim reference11 As Reference
Set reference11 = product1.CreateReferenceFromName("Product1/DM.2/!Axis:(Selection_RSur:(Face:(Brp:(Pocket.2;0:(Brp:(Sketch.3;8)));None:();Cf11:());Pocket.2_ResultOUT;Z0;G4162))")

Dim reference12 As Reference
Set reference12 = product1.CreateReferenceFromName("Product1/Plate.1/!Axis:(Selection_RSur:(Face:(Brp:(Pad.1;0:(Brp:(Sketch.1;15)));None:();Cf11:());Pad.1_ResultOUT;Z0;G4162))")

Dim constraint7 As Constraint
Set constraint7 = constraints1.AddBiEltCst(catCstTypeOn, reference11, reference12)

Set constraints1 = product1.Connections("CATIAConstraints")

Dim reference13 As Reference
Set reference13 = product1.CreateReferenceFromName("Product1/DM.2/!Axis:(Selection_RSur:(Face:(Brp:(Pocket.2;0:(Brp:(Sketch.3;6)));None:();Cf11:());Pocket.2_ResultOUT;Z0;G4162))")

Dim reference14 As Reference
Set reference14 = product1.CreateReferenceFromName("Product1/Plate.1/!Axis:(Selection_RSur:(Face:(Brp:(Pad.1;0:(Brp:(Sketch.1;13)));None:();Cf11:());Pad.1_ResultOUT;Z0;G4162))")

Dim constraint8 As Constraint
Set constraint8 = constraints1.AddBiEltCst(catCstTypeOn, reference13, reference14)

Set constraints1 = product1.Connections("CATIAConstraints")

Dim reference15 As Reference
Set reference15 = product1.CreateReferenceFromName("Product1/DM.2/!Axis:(Selection_RSur:(Face:(Brp:(Pocket.2;0:(Brp:(Sketch.3;4)));None:();Cf11:());Pocket.2_ResultOUT;Z0;G4162))")

Dim reference16 As Reference
Set reference16 = product1.CreateReferenceFromName("Product1/Plate.1/!Axis:(Selection_RSur:(Face:(Brp:(Pad.1;0:(Brp:(Sketch.1;11)));None:();Cf11:());Pad.1_ResultOUT;Z0;G4162))")

Dim constraint9 As Constraint
Set constraint9 = constraints1.AddBiEltCst(catCstTypeOn, reference15, reference16)

Set constraints1 = product1.Connections("CATIAConstraints")

Set reference10 = product1.CreateReferenceFromName("Product1/Plate.1/!Selection_RSur:(Face:(Brp:(Pad.1;2);None:();Cf11:());Pad.1_ResultOUT;Z0;G4162)")

Dim reference17 As Reference
Set reference17 = product1.CreateReferenceFromName("Product1/DM.2/!Selection_RSur:(Face:(Brp:(Pad.1;0:(Brp:(Sketch.1;4)));None:();Cf11:());Pocket.2_ResultOUT;Z0;G4162)")

Dim constraint10 As Constraint
Set constraint10 = constraints1.AddBiEltCst(catCstTypeSurfContact, reference10, reference17)

product1.Update 

product1.PartNumber = "A2"


Dim arrayOfVariantOfBSTR5(0)
arrayOfVariantOfBSTR5(0) = ".\SubAssembly\Nut.CATPart"
products1.AddComponentsFromFiles arrayOfVariantOfBSTR5, "All"

Dim specsAndGeomWindow1 As Window
Set specsAndGeomWindow1 = CATIA.ActiveWindow

Dim viewer3D1 As Viewer
Set viewer3D1 = specsAndGeomWindow1.ActiveViewer

Dim viewpoint3D1 As Viewpoint3D
Set viewpoint3D1 = viewer3D1.Viewpoint3D

Dim product3 As Product
Set product3 = products1.Item("Nut.1")

Dim move1 As Move
Set move1 = product3.Move

Set move1 = move1.MovableObject

Dim arrayOfVariantOfDouble1(11)
arrayOfVariantOfDouble1(0) = 1.000000
arrayOfVariantOfDouble1(1) = 0.000000
arrayOfVariantOfDouble1(2) = 0.000000
arrayOfVariantOfDouble1(3) = 0.000000
arrayOfVariantOfDouble1(4) = 1.000000
arrayOfVariantOfDouble1(5) = 0.000000
arrayOfVariantOfDouble1(6) = 0.000000
arrayOfVariantOfDouble1(7) = 0.000000
arrayOfVariantOfDouble1(8) = 1.000000
arrayOfVariantOfDouble1(9) = -2.565541
arrayOfVariantOfDouble1(10) = 0.000000
arrayOfVariantOfDouble1(11) = 0.000000
move1.Apply arrayOfVariantOfDouble1

Set move1 = product3.Move

Set move1 = move1.MovableObject

Dim arrayOfVariantOfDouble2(11)
arrayOfVariantOfDouble2(0) = 1.000000
arrayOfVariantOfDouble2(1) = 0.000000
arrayOfVariantOfDouble2(2) = 0.000000
arrayOfVariantOfDouble2(3) = 0.000000
arrayOfVariantOfDouble2(4) = 1.000000
arrayOfVariantOfDouble2(5) = 0.000000
arrayOfVariantOfDouble2(6) = 0.000000
arrayOfVariantOfDouble2(7) = 0.000000
arrayOfVariantOfDouble2(8) = 1.000000
arrayOfVariantOfDouble2(9) = -0.043648
arrayOfVariantOfDouble2(10) = 0.000000
arrayOfVariantOfDouble2(11) = 0.000000
move1.Apply arrayOfVariantOfDouble2

Set move1 = product3.Move

Set move1 = move1.MovableObject

Dim arrayOfVariantOfDouble3(11)
arrayOfVariantOfDouble3(0) = 1.000000
arrayOfVariantOfDouble3(1) = 0.000000
arrayOfVariantOfDouble3(2) = 0.000000
arrayOfVariantOfDouble3(3) = 0.000000
arrayOfVariantOfDouble3(4) = 1.000000
arrayOfVariantOfDouble3(5) = 0.000000
arrayOfVariantOfDouble3(6) = 0.000000
arrayOfVariantOfDouble3(7) = 0.000000
arrayOfVariantOfDouble3(8) = 1.000000
arrayOfVariantOfDouble3(9) = -0.376578
arrayOfVariantOfDouble3(10) = 0.000000
arrayOfVariantOfDouble3(11) = 0.000000
move1.Apply arrayOfVariantOfDouble3

Set move1 = product3.Move

Set move1 = move1.MovableObject

Dim arrayOfVariantOfDouble4(11)
arrayOfVariantOfDouble4(0) = 1.000000
arrayOfVariantOfDouble4(1) = 0.000000
arrayOfVariantOfDouble4(2) = 0.000000
arrayOfVariantOfDouble4(3) = 0.000000
arrayOfVariantOfDouble4(4) = 1.000000
arrayOfVariantOfDouble4(5) = 0.000000
arrayOfVariantOfDouble4(6) = 0.000000
arrayOfVariantOfDouble4(7) = 0.000000
arrayOfVariantOfDouble4(8) = 1.000000
arrayOfVariantOfDouble4(9) = -0.043648
arrayOfVariantOfDouble4(10) = 0.000000
arrayOfVariantOfDouble4(11) = 0.000000
move1.Apply arrayOfVariantOfDouble4

Set move1 = product3.Move

Set move1 = move1.MovableObject

Dim arrayOfVariantOfDouble5(11)
arrayOfVariantOfDouble5(0) = 1.000000
arrayOfVariantOfDouble5(1) = 0.000000
arrayOfVariantOfDouble5(2) = 0.000000
arrayOfVariantOfDouble5(3) = 0.000000
arrayOfVariantOfDouble5(4) = 1.000000
arrayOfVariantOfDouble5(5) = 0.000000
arrayOfVariantOfDouble5(6) = 0.000000
arrayOfVariantOfDouble5(7) = 0.000000
arrayOfVariantOfDouble5(8) = 1.000000
arrayOfVariantOfDouble5(9) = -0.753169
arrayOfVariantOfDouble5(10) = 0.000000
arrayOfVariantOfDouble5(11) = 0.000000
move1.Apply arrayOfVariantOfDouble5

Set move1 = product3.Move

Set move1 = move1.MovableObject

Dim arrayOfVariantOfDouble6(11)
arrayOfVariantOfDouble6(0) = 1.000000
arrayOfVariantOfDouble6(1) = 0.000000
arrayOfVariantOfDouble6(2) = 0.000000
arrayOfVariantOfDouble6(3) = 0.000000
arrayOfVariantOfDouble6(4) = 1.000000
arrayOfVariantOfDouble6(5) = 0.000000
arrayOfVariantOfDouble6(6) = 0.000000
arrayOfVariantOfDouble6(7) = 0.000000
arrayOfVariantOfDouble6(8) = 1.000000
arrayOfVariantOfDouble6(9) = -0.043648
arrayOfVariantOfDouble6(10) = 0.000000
arrayOfVariantOfDouble6(11) = 0.000000
move1.Apply arrayOfVariantOfDouble6

Set move1 = product3.Move

Set move1 = move1.MovableObject

Dim arrayOfVariantOfDouble7(11)
arrayOfVariantOfDouble7(0) = 1.000000
arrayOfVariantOfDouble7(1) = 0.000000
arrayOfVariantOfDouble7(2) = 0.000000
arrayOfVariantOfDouble7(3) = 0.000000
arrayOfVariantOfDouble7(4) = 1.000000
arrayOfVariantOfDouble7(5) = 0.000000
arrayOfVariantOfDouble7(6) = 0.000000
arrayOfVariantOfDouble7(7) = 0.000000
arrayOfVariantOfDouble7(8) = 1.000000
arrayOfVariantOfDouble7(9) = -0.376578
arrayOfVariantOfDouble7(10) = 0.000000
arrayOfVariantOfDouble7(11) = 0.000000
move1.Apply arrayOfVariantOfDouble7

Set move1 = product3.Move

Set move1 = move1.MovableObject

Dim arrayOfVariantOfDouble8(11)
arrayOfVariantOfDouble8(0) = 1.000000
arrayOfVariantOfDouble8(1) = 0.000000
arrayOfVariantOfDouble8(2) = 0.000000
arrayOfVariantOfDouble8(3) = 0.000000
arrayOfVariantOfDouble8(4) = 1.000000
arrayOfVariantOfDouble8(5) = 0.000000
arrayOfVariantOfDouble8(6) = 0.000000
arrayOfVariantOfDouble8(7) = 0.000000
arrayOfVariantOfDouble8(8) = 1.000000
arrayOfVariantOfDouble8(9) = -0.376583
arrayOfVariantOfDouble8(10) = 0.000000
arrayOfVariantOfDouble8(11) = 0.000000
move1.Apply arrayOfVariantOfDouble8

Set move1 = product3.Move

Set move1 = move1.MovableObject

Dim arrayOfVariantOfDouble9(11)
arrayOfVariantOfDouble9(0) = 1.000000
arrayOfVariantOfDouble9(1) = 0.000000
arrayOfVariantOfDouble9(2) = 0.000000
arrayOfVariantOfDouble9(3) = 0.000000
arrayOfVariantOfDouble9(4) = 1.000000
arrayOfVariantOfDouble9(5) = 0.000000
arrayOfVariantOfDouble9(6) = 0.000000
arrayOfVariantOfDouble9(7) = 0.000000
arrayOfVariantOfDouble9(8) = 1.000000
arrayOfVariantOfDouble9(9) = -0.376579
arrayOfVariantOfDouble9(10) = 0.000000
arrayOfVariantOfDouble9(11) = 0.000000
move1.Apply arrayOfVariantOfDouble9

Set move1 = product3.Move

Set move1 = move1.MovableObject

Dim arrayOfVariantOfDouble10(11)
arrayOfVariantOfDouble10(0) = 1.000000
arrayOfVariantOfDouble10(1) = 0.000000
arrayOfVariantOfDouble10(2) = 0.000000
arrayOfVariantOfDouble10(3) = 0.000000
arrayOfVariantOfDouble10(4) = 1.000000
arrayOfVariantOfDouble10(5) = 0.000000
arrayOfVariantOfDouble10(6) = 0.000000
arrayOfVariantOfDouble10(7) = 0.000000
arrayOfVariantOfDouble10(8) = 1.000000
arrayOfVariantOfDouble10(9) = -0.043648
arrayOfVariantOfDouble10(10) = 0.000000
arrayOfVariantOfDouble10(11) = 0.000000
move1.Apply arrayOfVariantOfDouble10

Set move1 = product3.Move

Set move1 = move1.MovableObject

Dim arrayOfVariantOfDouble11(11)
arrayOfVariantOfDouble11(0) = 1.000000
arrayOfVariantOfDouble11(1) = 0.000000
arrayOfVariantOfDouble11(2) = 0.000000
arrayOfVariantOfDouble11(3) = 0.000000
arrayOfVariantOfDouble11(4) = 1.000000
arrayOfVariantOfDouble11(5) = 0.000000
arrayOfVariantOfDouble11(6) = 0.000000
arrayOfVariantOfDouble11(7) = 0.000000
arrayOfVariantOfDouble11(8) = 1.000000
arrayOfVariantOfDouble11(9) = -0.376585
arrayOfVariantOfDouble11(10) = 0.000000
arrayOfVariantOfDouble11(11) = 0.000000
move1.Apply arrayOfVariantOfDouble11

Set move1 = product3.Move

Set move1 = move1.MovableObject

Dim arrayOfVariantOfDouble12(11)
arrayOfVariantOfDouble12(0) = 1.000000
arrayOfVariantOfDouble12(1) = 0.000000
arrayOfVariantOfDouble12(2) = 0.000000
arrayOfVariantOfDouble12(3) = 0.000000
arrayOfVariantOfDouble12(4) = 1.000000
arrayOfVariantOfDouble12(5) = 0.000000
arrayOfVariantOfDouble12(6) = 0.000000
arrayOfVariantOfDouble12(7) = 0.000000
arrayOfVariantOfDouble12(8) = 1.000000
arrayOfVariantOfDouble12(9) = -0.376579
arrayOfVariantOfDouble12(10) = 0.000000
arrayOfVariantOfDouble12(11) = 0.000000
move1.Apply arrayOfVariantOfDouble12

Set move1 = product3.Move

Set move1 = move1.MovableObject

Dim arrayOfVariantOfDouble13(11)
arrayOfVariantOfDouble13(0) = 1.000000
arrayOfVariantOfDouble13(1) = 0.000000
arrayOfVariantOfDouble13(2) = 0.000000
arrayOfVariantOfDouble13(3) = 0.000000
arrayOfVariantOfDouble13(4) = 1.000000
arrayOfVariantOfDouble13(5) = 0.000000
arrayOfVariantOfDouble13(6) = 0.000000
arrayOfVariantOfDouble13(7) = 0.000000
arrayOfVariantOfDouble13(8) = 1.000000
arrayOfVariantOfDouble13(9) = -0.376581
arrayOfVariantOfDouble13(10) = 0.000000
arrayOfVariantOfDouble13(11) = 0.000000
move1.Apply arrayOfVariantOfDouble13

Set move1 = product3.Move

Set move1 = move1.MovableObject

Dim arrayOfVariantOfDouble14(11)
arrayOfVariantOfDouble14(0) = 1.000000
arrayOfVariantOfDouble14(1) = 0.000000
arrayOfVariantOfDouble14(2) = 0.000000
arrayOfVariantOfDouble14(3) = 0.000000
arrayOfVariantOfDouble14(4) = 1.000000
arrayOfVariantOfDouble14(5) = 0.000000
arrayOfVariantOfDouble14(6) = 0.000000
arrayOfVariantOfDouble14(7) = 0.000000
arrayOfVariantOfDouble14(8) = 1.000000
arrayOfVariantOfDouble14(9) = -0.376581
arrayOfVariantOfDouble14(10) = 0.000000
arrayOfVariantOfDouble14(11) = 0.000000
move1.Apply arrayOfVariantOfDouble14

Set move1 = product3.Move

Set move1 = move1.MovableObject

Dim arrayOfVariantOfDouble15(11)
arrayOfVariantOfDouble15(0) = 1.000000
arrayOfVariantOfDouble15(1) = 0.000000
arrayOfVariantOfDouble15(2) = 0.000000
arrayOfVariantOfDouble15(3) = 0.000000
arrayOfVariantOfDouble15(4) = 1.000000
arrayOfVariantOfDouble15(5) = 0.000000
arrayOfVariantOfDouble15(6) = 0.000000
arrayOfVariantOfDouble15(7) = 0.000000
arrayOfVariantOfDouble15(8) = 1.000000
arrayOfVariantOfDouble15(9) = -0.376577
arrayOfVariantOfDouble15(10) = 0.000000
arrayOfVariantOfDouble15(11) = 0.000000
move1.Apply arrayOfVariantOfDouble15

Set move1 = product3.Move

Set move1 = move1.MovableObject

Dim arrayOfVariantOfDouble16(11)
arrayOfVariantOfDouble16(0) = 1.000000
arrayOfVariantOfDouble16(1) = 0.000000
arrayOfVariantOfDouble16(2) = 0.000000
arrayOfVariantOfDouble16(3) = 0.000000
arrayOfVariantOfDouble16(4) = 1.000000
arrayOfVariantOfDouble16(5) = 0.000000
arrayOfVariantOfDouble16(6) = 0.000000
arrayOfVariantOfDouble16(7) = 0.000000
arrayOfVariantOfDouble16(8) = 1.000000
arrayOfVariantOfDouble16(9) = -0.043652
arrayOfVariantOfDouble16(10) = 0.000000
arrayOfVariantOfDouble16(11) = 0.000000
move1.Apply arrayOfVariantOfDouble16

Set move1 = product3.Move

Set move1 = move1.MovableObject

Dim arrayOfVariantOfDouble17(11)
arrayOfVariantOfDouble17(0) = 1.000000
arrayOfVariantOfDouble17(1) = 0.000000
arrayOfVariantOfDouble17(2) = 0.000000
arrayOfVariantOfDouble17(3) = 0.000000
arrayOfVariantOfDouble17(4) = 1.000000
arrayOfVariantOfDouble17(5) = 0.000000
arrayOfVariantOfDouble17(6) = 0.000000
arrayOfVariantOfDouble17(7) = 0.000000
arrayOfVariantOfDouble17(8) = 1.000000
arrayOfVariantOfDouble17(9) = -0.376583
arrayOfVariantOfDouble17(10) = 0.000000
arrayOfVariantOfDouble17(11) = 0.000000
move1.Apply arrayOfVariantOfDouble17

Set move1 = product3.Move

Set move1 = move1.MovableObject

Dim arrayOfVariantOfDouble18(11)
arrayOfVariantOfDouble18(0) = 1.000000
arrayOfVariantOfDouble18(1) = 0.000000
arrayOfVariantOfDouble18(2) = 0.000000
arrayOfVariantOfDouble18(3) = 0.000000
arrayOfVariantOfDouble18(4) = 1.000000
arrayOfVariantOfDouble18(5) = 0.000000
arrayOfVariantOfDouble18(6) = 0.000000
arrayOfVariantOfDouble18(7) = 0.000000
arrayOfVariantOfDouble18(8) = 1.000000
arrayOfVariantOfDouble18(9) = -0.376579
arrayOfVariantOfDouble18(10) = 0.000000
arrayOfVariantOfDouble18(11) = 0.000000
move1.Apply arrayOfVariantOfDouble18

Set move1 = product3.Move

Set move1 = move1.MovableObject

Dim arrayOfVariantOfDouble19(11)
arrayOfVariantOfDouble19(0) = 1.000000
arrayOfVariantOfDouble19(1) = 0.000000
arrayOfVariantOfDouble19(2) = 0.000000
arrayOfVariantOfDouble19(3) = 0.000000
arrayOfVariantOfDouble19(4) = 1.000000
arrayOfVariantOfDouble19(5) = 0.000000
arrayOfVariantOfDouble19(6) = 0.000000
arrayOfVariantOfDouble19(7) = 0.000000
arrayOfVariantOfDouble19(8) = 1.000000
arrayOfVariantOfDouble19(9) = -0.420232
arrayOfVariantOfDouble19(10) = 0.000000
arrayOfVariantOfDouble19(11) = 0.000000
move1.Apply arrayOfVariantOfDouble19

Set move1 = product3.Move

Set move1 = move1.MovableObject

Dim arrayOfVariantOfDouble20(11)
arrayOfVariantOfDouble20(0) = 1.000000
arrayOfVariantOfDouble20(1) = 0.000000
arrayOfVariantOfDouble20(2) = 0.000000
arrayOfVariantOfDouble20(3) = 0.000000
arrayOfVariantOfDouble20(4) = 1.000000
arrayOfVariantOfDouble20(5) = 0.000000
arrayOfVariantOfDouble20(6) = 0.000000
arrayOfVariantOfDouble20(7) = 0.000000
arrayOfVariantOfDouble20(8) = 1.000000
arrayOfVariantOfDouble20(9) = -0.376580
arrayOfVariantOfDouble20(10) = 0.000000
arrayOfVariantOfDouble20(11) = 0.000000
move1.Apply arrayOfVariantOfDouble20

Set move1 = product3.Move

Set move1 = move1.MovableObject

Dim arrayOfVariantOfDouble21(11)
arrayOfVariantOfDouble21(0) = 1.000000
arrayOfVariantOfDouble21(1) = 0.000000
arrayOfVariantOfDouble21(2) = 0.000000
arrayOfVariantOfDouble21(3) = 0.000000
arrayOfVariantOfDouble21(4) = 1.000000
arrayOfVariantOfDouble21(5) = 0.000000
arrayOfVariantOfDouble21(6) = 0.000000
arrayOfVariantOfDouble21(7) = 0.000000
arrayOfVariantOfDouble21(8) = 1.000000
arrayOfVariantOfDouble21(9) = -0.376579
arrayOfVariantOfDouble21(10) = 0.000000
arrayOfVariantOfDouble21(11) = 0.000000
move1.Apply arrayOfVariantOfDouble21

Set move1 = product3.Move

Set move1 = move1.MovableObject

Dim arrayOfVariantOfDouble22(11)
arrayOfVariantOfDouble22(0) = 1.000000
arrayOfVariantOfDouble22(1) = 0.000000
arrayOfVariantOfDouble22(2) = 0.000000
arrayOfVariantOfDouble22(3) = 0.000000
arrayOfVariantOfDouble22(4) = 1.000000
arrayOfVariantOfDouble22(5) = 0.000000
arrayOfVariantOfDouble22(6) = 0.000000
arrayOfVariantOfDouble22(7) = 0.000000
arrayOfVariantOfDouble22(8) = 1.000000
arrayOfVariantOfDouble22(9) = -0.376584
arrayOfVariantOfDouble22(10) = 0.000000
arrayOfVariantOfDouble22(11) = 0.000000
move1.Apply arrayOfVariantOfDouble22

Set move1 = product3.Move

Set move1 = move1.MovableObject

Dim arrayOfVariantOfDouble23(11)
arrayOfVariantOfDouble23(0) = 1.000000
arrayOfVariantOfDouble23(1) = 0.000000
arrayOfVariantOfDouble23(2) = 0.000000
arrayOfVariantOfDouble23(3) = 0.000000
arrayOfVariantOfDouble23(4) = 1.000000
arrayOfVariantOfDouble23(5) = 0.000000
arrayOfVariantOfDouble23(6) = 0.000000
arrayOfVariantOfDouble23(7) = 0.000000
arrayOfVariantOfDouble23(8) = 1.000000
arrayOfVariantOfDouble23(9) = -0.376577
arrayOfVariantOfDouble23(10) = 0.000000
arrayOfVariantOfDouble23(11) = 0.000000
move1.Apply arrayOfVariantOfDouble23

Set move1 = product3.Move

Set move1 = move1.MovableObject

Dim arrayOfVariantOfDouble24(11)
arrayOfVariantOfDouble24(0) = 1.000000
arrayOfVariantOfDouble24(1) = 0.000000
arrayOfVariantOfDouble24(2) = 0.000000
arrayOfVariantOfDouble24(3) = 0.000000
arrayOfVariantOfDouble24(4) = 1.000000
arrayOfVariantOfDouble24(5) = 0.000000
arrayOfVariantOfDouble24(6) = 0.000000
arrayOfVariantOfDouble24(7) = 0.000000
arrayOfVariantOfDouble24(8) = 1.000000
arrayOfVariantOfDouble24(9) = -0.376583
arrayOfVariantOfDouble24(10) = 0.000000
arrayOfVariantOfDouble24(11) = 0.000000
move1.Apply arrayOfVariantOfDouble24

Set move1 = product3.Move

Set move1 = move1.MovableObject

Dim arrayOfVariantOfDouble25(11)
arrayOfVariantOfDouble25(0) = 1.000000
arrayOfVariantOfDouble25(1) = 0.000000
arrayOfVariantOfDouble25(2) = 0.000000
arrayOfVariantOfDouble25(3) = 0.000000
arrayOfVariantOfDouble25(4) = 1.000000
arrayOfVariantOfDouble25(5) = 0.000000
arrayOfVariantOfDouble25(6) = 0.000000
arrayOfVariantOfDouble25(7) = 0.000000
arrayOfVariantOfDouble25(8) = 1.000000
arrayOfVariantOfDouble25(9) = -0.376587
arrayOfVariantOfDouble25(10) = 0.000000
arrayOfVariantOfDouble25(11) = 0.000000
move1.Apply arrayOfVariantOfDouble25

Set move1 = product3.Move

Set move1 = move1.MovableObject

Dim arrayOfVariantOfDouble26(11)
arrayOfVariantOfDouble26(0) = 1.000000
arrayOfVariantOfDouble26(1) = 0.000000
arrayOfVariantOfDouble26(2) = 0.000000
arrayOfVariantOfDouble26(3) = 0.000000
arrayOfVariantOfDouble26(4) = 1.000000
arrayOfVariantOfDouble26(5) = 0.000000
arrayOfVariantOfDouble26(6) = 0.000000
arrayOfVariantOfDouble26(7) = 0.000000
arrayOfVariantOfDouble26(8) = 1.000000
arrayOfVariantOfDouble26(9) = -0.376578
arrayOfVariantOfDouble26(10) = 0.000000
arrayOfVariantOfDouble26(11) = 0.000000
move1.Apply arrayOfVariantOfDouble26

Set move1 = product3.Move

Set move1 = move1.MovableObject

Dim arrayOfVariantOfDouble27(11)
arrayOfVariantOfDouble27(0) = 1.000000
arrayOfVariantOfDouble27(1) = 0.000000
arrayOfVariantOfDouble27(2) = 0.000000
arrayOfVariantOfDouble27(3) = 0.000000
arrayOfVariantOfDouble27(4) = 1.000000
arrayOfVariantOfDouble27(5) = 0.000000
arrayOfVariantOfDouble27(6) = 0.000000
arrayOfVariantOfDouble27(7) = 0.000000
arrayOfVariantOfDouble27(8) = 1.000000
arrayOfVariantOfDouble27(9) = -0.376580
arrayOfVariantOfDouble27(10) = 0.000000
arrayOfVariantOfDouble27(11) = 0.000000
move1.Apply arrayOfVariantOfDouble27

Set move1 = product3.Move

Set move1 = move1.MovableObject

Dim arrayOfVariantOfDouble28(11)
arrayOfVariantOfDouble28(0) = 1.000000
arrayOfVariantOfDouble28(1) = 0.000000
arrayOfVariantOfDouble28(2) = 0.000000
arrayOfVariantOfDouble28(3) = 0.000000
arrayOfVariantOfDouble28(4) = 1.000000
arrayOfVariantOfDouble28(5) = 0.000000
arrayOfVariantOfDouble28(6) = 0.000000
arrayOfVariantOfDouble28(7) = 0.000000
arrayOfVariantOfDouble28(8) = 1.000000
arrayOfVariantOfDouble28(9) = -0.376583
arrayOfVariantOfDouble28(10) = 0.000000
arrayOfVariantOfDouble28(11) = 0.000000
move1.Apply arrayOfVariantOfDouble28

Set move1 = product3.Move

Set move1 = move1.MovableObject

Dim arrayOfVariantOfDouble29(11)
arrayOfVariantOfDouble29(0) = 1.000000
arrayOfVariantOfDouble29(1) = 0.000000
arrayOfVariantOfDouble29(2) = 0.000000
arrayOfVariantOfDouble29(3) = 0.000000
arrayOfVariantOfDouble29(4) = 1.000000
arrayOfVariantOfDouble29(5) = 0.000000
arrayOfVariantOfDouble29(6) = 0.000000
arrayOfVariantOfDouble29(7) = 0.000000
arrayOfVariantOfDouble29(8) = 1.000000
arrayOfVariantOfDouble29(9) = -0.043646
arrayOfVariantOfDouble29(10) = 0.000000
arrayOfVariantOfDouble29(11) = 0.000000
move1.Apply arrayOfVariantOfDouble29

Set move1 = product3.Move

Set move1 = move1.MovableObject

Dim arrayOfVariantOfDouble30(11)
arrayOfVariantOfDouble30(0) = 1.000000
arrayOfVariantOfDouble30(1) = 0.000000
arrayOfVariantOfDouble30(2) = 0.000000
arrayOfVariantOfDouble30(3) = 0.000000
arrayOfVariantOfDouble30(4) = 1.000000
arrayOfVariantOfDouble30(5) = 0.000000
arrayOfVariantOfDouble30(6) = 0.000000
arrayOfVariantOfDouble30(7) = 0.000000
arrayOfVariantOfDouble30(8) = 1.000000
arrayOfVariantOfDouble30(9) = -0.376582
arrayOfVariantOfDouble30(10) = 0.000000
arrayOfVariantOfDouble30(11) = 0.000000
move1.Apply arrayOfVariantOfDouble30

Set move1 = product3.Move

Set move1 = move1.MovableObject

Dim arrayOfVariantOfDouble31(11)
arrayOfVariantOfDouble31(0) = 1.000000
arrayOfVariantOfDouble31(1) = 0.000000
arrayOfVariantOfDouble31(2) = 0.000000
arrayOfVariantOfDouble31(3) = 0.000000
arrayOfVariantOfDouble31(4) = 1.000000
arrayOfVariantOfDouble31(5) = 0.000000
arrayOfVariantOfDouble31(6) = 0.000000
arrayOfVariantOfDouble31(7) = 0.000000
arrayOfVariantOfDouble31(8) = 1.000000
arrayOfVariantOfDouble31(9) = -0.376577
arrayOfVariantOfDouble31(10) = 0.000000
arrayOfVariantOfDouble31(11) = 0.000000
move1.Apply arrayOfVariantOfDouble31

Set move1 = product3.Move

Set move1 = move1.MovableObject

Dim arrayOfVariantOfDouble32(11)
arrayOfVariantOfDouble32(0) = 1.000000
arrayOfVariantOfDouble32(1) = 0.000000
arrayOfVariantOfDouble32(2) = 0.000000
arrayOfVariantOfDouble32(3) = 0.000000
arrayOfVariantOfDouble32(4) = 1.000000
arrayOfVariantOfDouble32(5) = 0.000000
arrayOfVariantOfDouble32(6) = 0.000000
arrayOfVariantOfDouble32(7) = 0.000000
arrayOfVariantOfDouble32(8) = 1.000000
arrayOfVariantOfDouble32(9) = -0.376583
arrayOfVariantOfDouble32(10) = 0.000000
arrayOfVariantOfDouble32(11) = 0.000000
move1.Apply arrayOfVariantOfDouble32

Set move1 = product3.Move

Set move1 = move1.MovableObject

Dim arrayOfVariantOfDouble33(11)
arrayOfVariantOfDouble33(0) = 1.000000
arrayOfVariantOfDouble33(1) = 0.000000
arrayOfVariantOfDouble33(2) = 0.000000
arrayOfVariantOfDouble33(3) = 0.000000
arrayOfVariantOfDouble33(4) = 1.000000
arrayOfVariantOfDouble33(5) = 0.000000
arrayOfVariantOfDouble33(6) = 0.000000
arrayOfVariantOfDouble33(7) = 0.000000
arrayOfVariantOfDouble33(8) = 1.000000
arrayOfVariantOfDouble33(9) = -0.376585
arrayOfVariantOfDouble33(10) = 0.000000
arrayOfVariantOfDouble33(11) = 0.000000
move1.Apply arrayOfVariantOfDouble33

Set move1 = product3.Move

Set move1 = move1.MovableObject

Dim arrayOfVariantOfDouble34(11)
arrayOfVariantOfDouble34(0) = 1.000000
arrayOfVariantOfDouble34(1) = 0.000000
arrayOfVariantOfDouble34(2) = 0.000000
arrayOfVariantOfDouble34(3) = 0.000000
arrayOfVariantOfDouble34(4) = 1.000000
arrayOfVariantOfDouble34(5) = 0.000000
arrayOfVariantOfDouble34(6) = 0.000000
arrayOfVariantOfDouble34(7) = 0.000000
arrayOfVariantOfDouble34(8) = 1.000000
arrayOfVariantOfDouble34(9) = -0.376579
arrayOfVariantOfDouble34(10) = 0.000000
arrayOfVariantOfDouble34(11) = 0.000000
move1.Apply arrayOfVariantOfDouble34

Set move1 = product3.Move

Set move1 = move1.MovableObject

Dim arrayOfVariantOfDouble35(11)
arrayOfVariantOfDouble35(0) = 1.000000
arrayOfVariantOfDouble35(1) = 0.000000
arrayOfVariantOfDouble35(2) = 0.000000
arrayOfVariantOfDouble35(3) = 0.000000
arrayOfVariantOfDouble35(4) = 1.000000
arrayOfVariantOfDouble35(5) = 0.000000
arrayOfVariantOfDouble35(6) = 0.000000
arrayOfVariantOfDouble35(7) = 0.000000
arrayOfVariantOfDouble35(8) = 1.000000
arrayOfVariantOfDouble35(9) = -0.376578
arrayOfVariantOfDouble35(10) = 0.000000
arrayOfVariantOfDouble35(11) = 0.000000
move1.Apply arrayOfVariantOfDouble35

Set move1 = product3.Move

Set move1 = move1.MovableObject

Dim arrayOfVariantOfDouble36(11)
arrayOfVariantOfDouble36(0) = 1.000000
arrayOfVariantOfDouble36(1) = 0.000000
arrayOfVariantOfDouble36(2) = 0.000000
arrayOfVariantOfDouble36(3) = 0.000000
arrayOfVariantOfDouble36(4) = 1.000000
arrayOfVariantOfDouble36(5) = 0.000000
arrayOfVariantOfDouble36(6) = 0.000000
arrayOfVariantOfDouble36(7) = 0.000000
arrayOfVariantOfDouble36(8) = 1.000000
arrayOfVariantOfDouble36(9) = -0.043653
arrayOfVariantOfDouble36(10) = 0.000000
arrayOfVariantOfDouble36(11) = 0.000000
move1.Apply arrayOfVariantOfDouble36

Set move1 = product3.Move

Set move1 = move1.MovableObject

Dim arrayOfVariantOfDouble37(11)
arrayOfVariantOfDouble37(0) = 1.000000
arrayOfVariantOfDouble37(1) = 0.000000
arrayOfVariantOfDouble37(2) = 0.000000
arrayOfVariantOfDouble37(3) = 0.000000
arrayOfVariantOfDouble37(4) = 1.000000
arrayOfVariantOfDouble37(5) = 0.000000
arrayOfVariantOfDouble37(6) = 0.000000
arrayOfVariantOfDouble37(7) = 0.000000
arrayOfVariantOfDouble37(8) = 1.000000
arrayOfVariantOfDouble37(9) = -0.753161
arrayOfVariantOfDouble37(10) = 0.000000
arrayOfVariantOfDouble37(11) = 0.000000
move1.Apply arrayOfVariantOfDouble37

Set move1 = product3.Move

Set move1 = move1.MovableObject

Dim arrayOfVariantOfDouble38(11)
arrayOfVariantOfDouble38(0) = 1.000000
arrayOfVariantOfDouble38(1) = 0.000000
arrayOfVariantOfDouble38(2) = 0.000000
arrayOfVariantOfDouble38(3) = 0.000000
arrayOfVariantOfDouble38(4) = 1.000000
arrayOfVariantOfDouble38(5) = 0.000000
arrayOfVariantOfDouble38(6) = 0.000000
arrayOfVariantOfDouble38(7) = 0.000000
arrayOfVariantOfDouble38(8) = 1.000000
arrayOfVariantOfDouble38(9) = -0.376583
arrayOfVariantOfDouble38(10) = 0.000000
arrayOfVariantOfDouble38(11) = 0.000000
move1.Apply arrayOfVariantOfDouble38

Set move1 = product3.Move

Set move1 = move1.MovableObject

Dim arrayOfVariantOfDouble39(11)
arrayOfVariantOfDouble39(0) = 1.000000
arrayOfVariantOfDouble39(1) = 0.000000
arrayOfVariantOfDouble39(2) = 0.000000
arrayOfVariantOfDouble39(3) = 0.000000
arrayOfVariantOfDouble39(4) = 1.000000
arrayOfVariantOfDouble39(5) = 0.000000
arrayOfVariantOfDouble39(6) = 0.000000
arrayOfVariantOfDouble39(7) = 0.000000
arrayOfVariantOfDouble39(8) = 1.000000
arrayOfVariantOfDouble39(9) = -0.376579
arrayOfVariantOfDouble39(10) = 0.000000
arrayOfVariantOfDouble39(11) = 0.000000
move1.Apply arrayOfVariantOfDouble39

Set move1 = product3.Move

Set move1 = move1.MovableObject

Dim arrayOfVariantOfDouble40(11)
arrayOfVariantOfDouble40(0) = 1.000000
arrayOfVariantOfDouble40(1) = 0.000000
arrayOfVariantOfDouble40(2) = 0.000000
arrayOfVariantOfDouble40(3) = 0.000000
arrayOfVariantOfDouble40(4) = 1.000000
arrayOfVariantOfDouble40(5) = 0.000000
arrayOfVariantOfDouble40(6) = 0.000000
arrayOfVariantOfDouble40(7) = 0.000000
arrayOfVariantOfDouble40(8) = 1.000000
arrayOfVariantOfDouble40(9) = -0.376584
arrayOfVariantOfDouble40(10) = 0.000000
arrayOfVariantOfDouble40(11) = 0.000000
move1.Apply arrayOfVariantOfDouble40

Set move1 = product3.Move

Set move1 = move1.MovableObject

Dim arrayOfVariantOfDouble41(11)
arrayOfVariantOfDouble41(0) = 1.000000
arrayOfVariantOfDouble41(1) = 0.000000
arrayOfVariantOfDouble41(2) = 0.000000
arrayOfVariantOfDouble41(3) = 0.000000
arrayOfVariantOfDouble41(4) = 1.000000
arrayOfVariantOfDouble41(5) = 0.000000
arrayOfVariantOfDouble41(6) = 0.000000
arrayOfVariantOfDouble41(7) = 0.000000
arrayOfVariantOfDouble41(8) = 1.000000
arrayOfVariantOfDouble41(9) = -0.376578
arrayOfVariantOfDouble41(10) = 0.000000
arrayOfVariantOfDouble41(11) = 0.000000
move1.Apply arrayOfVariantOfDouble41

Set move1 = product3.Move

Set move1 = move1.MovableObject

Dim arrayOfVariantOfDouble42(11)
arrayOfVariantOfDouble42(0) = 1.000000
arrayOfVariantOfDouble42(1) = 0.000000
arrayOfVariantOfDouble42(2) = 0.000000
arrayOfVariantOfDouble42(3) = 0.000000
arrayOfVariantOfDouble42(4) = 1.000000
arrayOfVariantOfDouble42(5) = 0.000000
arrayOfVariantOfDouble42(6) = 0.000000
arrayOfVariantOfDouble42(7) = 0.000000
arrayOfVariantOfDouble42(8) = 1.000000
arrayOfVariantOfDouble42(9) = -0.376580
arrayOfVariantOfDouble42(10) = 0.000000
arrayOfVariantOfDouble42(11) = 0.000000
move1.Apply arrayOfVariantOfDouble42

Set move1 = product3.Move

Set move1 = move1.MovableObject

Dim arrayOfVariantOfDouble43(11)
arrayOfVariantOfDouble43(0) = 1.000000
arrayOfVariantOfDouble43(1) = 0.000000
arrayOfVariantOfDouble43(2) = 0.000000
arrayOfVariantOfDouble43(3) = 0.000000
arrayOfVariantOfDouble43(4) = 1.000000
arrayOfVariantOfDouble43(5) = 0.000000
arrayOfVariantOfDouble43(6) = 0.000000
arrayOfVariantOfDouble43(7) = 0.000000
arrayOfVariantOfDouble43(8) = 1.000000
arrayOfVariantOfDouble43(9) = -0.376583
arrayOfVariantOfDouble43(10) = 0.000000
arrayOfVariantOfDouble43(11) = 0.000000
move1.Apply arrayOfVariantOfDouble43

Set move1 = product3.Move

Set move1 = move1.MovableObject

Dim arrayOfVariantOfDouble44(11)
arrayOfVariantOfDouble44(0) = 1.000000
arrayOfVariantOfDouble44(1) = 0.000000
arrayOfVariantOfDouble44(2) = 0.000000
arrayOfVariantOfDouble44(3) = 0.000000
arrayOfVariantOfDouble44(4) = 1.000000
arrayOfVariantOfDouble44(5) = 0.000000
arrayOfVariantOfDouble44(6) = 0.000000
arrayOfVariantOfDouble44(7) = 0.000000
arrayOfVariantOfDouble44(8) = 1.000000
arrayOfVariantOfDouble44(9) = -0.376579
arrayOfVariantOfDouble44(10) = 0.000000
arrayOfVariantOfDouble44(11) = 0.000000
move1.Apply arrayOfVariantOfDouble44

Set move1 = product3.Move

Set move1 = move1.MovableObject

Dim arrayOfVariantOfDouble45(11)
arrayOfVariantOfDouble45(0) = 1.000000
arrayOfVariantOfDouble45(1) = 0.000000
arrayOfVariantOfDouble45(2) = 0.000000
arrayOfVariantOfDouble45(3) = 0.000000
arrayOfVariantOfDouble45(4) = 1.000000
arrayOfVariantOfDouble45(5) = 0.000000
arrayOfVariantOfDouble45(6) = 0.000000
arrayOfVariantOfDouble45(7) = 0.000000
arrayOfVariantOfDouble45(8) = 1.000000
arrayOfVariantOfDouble45(9) = -0.376585
arrayOfVariantOfDouble45(10) = 0.000000
arrayOfVariantOfDouble45(11) = 0.000000
move1.Apply arrayOfVariantOfDouble45

Set move1 = product3.Move

Set move1 = move1.MovableObject

Dim arrayOfVariantOfDouble46(11)
arrayOfVariantOfDouble46(0) = 1.000000
arrayOfVariantOfDouble46(1) = 0.000000
arrayOfVariantOfDouble46(2) = 0.000000
arrayOfVariantOfDouble46(3) = 0.000000
arrayOfVariantOfDouble46(4) = 1.000000
arrayOfVariantOfDouble46(5) = 0.000000
arrayOfVariantOfDouble46(6) = 0.000000
arrayOfVariantOfDouble46(7) = 0.000000
arrayOfVariantOfDouble46(8) = 1.000000
arrayOfVariantOfDouble46(9) = -0.376580
arrayOfVariantOfDouble46(10) = 0.000000
arrayOfVariantOfDouble46(11) = 0.000000
move1.Apply arrayOfVariantOfDouble46

Set move1 = product3.Move

Set move1 = move1.MovableObject

Dim arrayOfVariantOfDouble47(11)
arrayOfVariantOfDouble47(0) = 1.000000
arrayOfVariantOfDouble47(1) = 0.000000
arrayOfVariantOfDouble47(2) = 0.000000
arrayOfVariantOfDouble47(3) = 0.000000
arrayOfVariantOfDouble47(4) = 1.000000
arrayOfVariantOfDouble47(5) = 0.000000
arrayOfVariantOfDouble47(6) = 0.000000
arrayOfVariantOfDouble47(7) = 0.000000
arrayOfVariantOfDouble47(8) = 1.000000
arrayOfVariantOfDouble47(9) = -0.420233
arrayOfVariantOfDouble47(10) = 0.000000
arrayOfVariantOfDouble47(11) = 0.000000
move1.Apply arrayOfVariantOfDouble47

Set move1 = product3.Move

Set move1 = move1.MovableObject

Dim arrayOfVariantOfDouble48(11)
arrayOfVariantOfDouble48(0) = 1.000000
arrayOfVariantOfDouble48(1) = 0.000000
arrayOfVariantOfDouble48(2) = 0.000000
arrayOfVariantOfDouble48(3) = 0.000000
arrayOfVariantOfDouble48(4) = 1.000000
arrayOfVariantOfDouble48(5) = 0.000000
arrayOfVariantOfDouble48(6) = 0.000000
arrayOfVariantOfDouble48(7) = 0.000000
arrayOfVariantOfDouble48(8) = 1.000000
arrayOfVariantOfDouble48(9) = -0.376576
arrayOfVariantOfDouble48(10) = 0.000000
arrayOfVariantOfDouble48(11) = 0.000000
move1.Apply arrayOfVariantOfDouble48

Set move1 = product3.Move

Set move1 = move1.MovableObject

Dim arrayOfVariantOfDouble49(11)
arrayOfVariantOfDouble49(0) = 1.000000
arrayOfVariantOfDouble49(1) = 0.000000
arrayOfVariantOfDouble49(2) = 0.000000
arrayOfVariantOfDouble49(3) = 0.000000
arrayOfVariantOfDouble49(4) = 1.000000
arrayOfVariantOfDouble49(5) = 0.000000
arrayOfVariantOfDouble49(6) = 0.000000
arrayOfVariantOfDouble49(7) = 0.000000
arrayOfVariantOfDouble49(8) = 1.000000
arrayOfVariantOfDouble49(9) = -0.376583
arrayOfVariantOfDouble49(10) = 0.000000
arrayOfVariantOfDouble49(11) = 0.000000
move1.Apply arrayOfVariantOfDouble49

Set move1 = product3.Move

Set move1 = move1.MovableObject

Dim arrayOfVariantOfDouble50(11)
arrayOfVariantOfDouble50(0) = 1.000000
arrayOfVariantOfDouble50(1) = 0.000000
arrayOfVariantOfDouble50(2) = 0.000000
arrayOfVariantOfDouble50(3) = 0.000000
arrayOfVariantOfDouble50(4) = 1.000000
arrayOfVariantOfDouble50(5) = 0.000000
arrayOfVariantOfDouble50(6) = 0.000000
arrayOfVariantOfDouble50(7) = 0.000000
arrayOfVariantOfDouble50(8) = 1.000000
arrayOfVariantOfDouble50(9) = -0.376582
arrayOfVariantOfDouble50(10) = 0.000000
arrayOfVariantOfDouble50(11) = 0.000000
move1.Apply arrayOfVariantOfDouble50

Set move1 = product3.Move

Set move1 = move1.MovableObject

Dim arrayOfVariantOfDouble51(11)
arrayOfVariantOfDouble51(0) = 1.000000
arrayOfVariantOfDouble51(1) = 0.000000
arrayOfVariantOfDouble51(2) = 0.000000
arrayOfVariantOfDouble51(3) = 0.000000
arrayOfVariantOfDouble51(4) = 1.000000
arrayOfVariantOfDouble51(5) = 0.000000
arrayOfVariantOfDouble51(6) = 0.000000
arrayOfVariantOfDouble51(7) = 0.000000
arrayOfVariantOfDouble51(8) = 1.000000
arrayOfVariantOfDouble51(9) = -0.376578
arrayOfVariantOfDouble51(10) = 0.000000
arrayOfVariantOfDouble51(11) = 0.000000
move1.Apply arrayOfVariantOfDouble51

Set move1 = product3.Move

Set move1 = move1.MovableObject

Dim arrayOfVariantOfDouble52(11)
arrayOfVariantOfDouble52(0) = 1.000000
arrayOfVariantOfDouble52(1) = 0.000000
arrayOfVariantOfDouble52(2) = 0.000000
arrayOfVariantOfDouble52(3) = 0.000000
arrayOfVariantOfDouble52(4) = 1.000000
arrayOfVariantOfDouble52(5) = 0.000000
arrayOfVariantOfDouble52(6) = 0.000000
arrayOfVariantOfDouble52(7) = 0.000000
arrayOfVariantOfDouble52(8) = 1.000000
arrayOfVariantOfDouble52(9) = -0.376580
arrayOfVariantOfDouble52(10) = 0.000000
arrayOfVariantOfDouble52(11) = 0.000000
move1.Apply arrayOfVariantOfDouble52

Set move1 = product3.Move

Set move1 = move1.MovableObject

Dim arrayOfVariantOfDouble53(11)
arrayOfVariantOfDouble53(0) = 1.000000
arrayOfVariantOfDouble53(1) = 0.000000
arrayOfVariantOfDouble53(2) = 0.000000
arrayOfVariantOfDouble53(3) = 0.000000
arrayOfVariantOfDouble53(4) = 1.000000
arrayOfVariantOfDouble53(5) = 0.000000
arrayOfVariantOfDouble53(6) = 0.000000
arrayOfVariantOfDouble53(7) = 0.000000
arrayOfVariantOfDouble53(8) = 1.000000
arrayOfVariantOfDouble53(9) = -0.376587
arrayOfVariantOfDouble53(10) = 0.000000
arrayOfVariantOfDouble53(11) = 0.000000
move1.Apply arrayOfVariantOfDouble53

Set move1 = product3.Move

Set move1 = move1.MovableObject

Dim arrayOfVariantOfDouble54(11)
arrayOfVariantOfDouble54(0) = 1.000000
arrayOfVariantOfDouble54(1) = 0.000000
arrayOfVariantOfDouble54(2) = 0.000000
arrayOfVariantOfDouble54(3) = 0.000000
arrayOfVariantOfDouble54(4) = 1.000000
arrayOfVariantOfDouble54(5) = 0.000000
arrayOfVariantOfDouble54(6) = 0.000000
arrayOfVariantOfDouble54(7) = 0.000000
arrayOfVariantOfDouble54(8) = 1.000000
arrayOfVariantOfDouble54(9) = -0.376579
arrayOfVariantOfDouble54(10) = 0.000000
arrayOfVariantOfDouble54(11) = 0.000000
move1.Apply arrayOfVariantOfDouble54

Set move1 = product3.Move

Set move1 = move1.MovableObject

Dim arrayOfVariantOfDouble55(11)
arrayOfVariantOfDouble55(0) = 1.000000
arrayOfVariantOfDouble55(1) = 0.000000
arrayOfVariantOfDouble55(2) = 0.000000
arrayOfVariantOfDouble55(3) = 0.000000
arrayOfVariantOfDouble55(4) = 1.000000
arrayOfVariantOfDouble55(5) = 0.000000
arrayOfVariantOfDouble55(6) = 0.000000
arrayOfVariantOfDouble55(7) = 0.000000
arrayOfVariantOfDouble55(8) = 1.000000
arrayOfVariantOfDouble55(9) = -0.376576
arrayOfVariantOfDouble55(10) = 0.000000
arrayOfVariantOfDouble55(11) = 0.000000
move1.Apply arrayOfVariantOfDouble55

Set move1 = product3.Move

Set move1 = move1.MovableObject

Dim arrayOfVariantOfDouble56(11)
arrayOfVariantOfDouble56(0) = 1.000000
arrayOfVariantOfDouble56(1) = 0.000000
arrayOfVariantOfDouble56(2) = 0.000000
arrayOfVariantOfDouble56(3) = 0.000000
arrayOfVariantOfDouble56(4) = 1.000000
arrayOfVariantOfDouble56(5) = 0.000000
arrayOfVariantOfDouble56(6) = 0.000000
arrayOfVariantOfDouble56(7) = 0.000000
arrayOfVariantOfDouble56(8) = 1.000000
arrayOfVariantOfDouble56(9) = -0.376590
arrayOfVariantOfDouble56(10) = 0.000000
arrayOfVariantOfDouble56(11) = 0.000000
move1.Apply arrayOfVariantOfDouble56

Set move1 = product3.Move

Set move1 = move1.MovableObject

Dim arrayOfVariantOfDouble57(11)
arrayOfVariantOfDouble57(0) = 1.000000
arrayOfVariantOfDouble57(1) = 0.000000
arrayOfVariantOfDouble57(2) = 0.000000
arrayOfVariantOfDouble57(3) = 0.000000
arrayOfVariantOfDouble57(4) = 1.000000
arrayOfVariantOfDouble57(5) = 0.000000
arrayOfVariantOfDouble57(6) = 0.000000
arrayOfVariantOfDouble57(7) = 0.000000
arrayOfVariantOfDouble57(8) = 1.000000
arrayOfVariantOfDouble57(9) = -0.376578
arrayOfVariantOfDouble57(10) = 0.000000
arrayOfVariantOfDouble57(11) = 0.000000
move1.Apply arrayOfVariantOfDouble57

Set move1 = product3.Move

Set move1 = move1.MovableObject

Dim arrayOfVariantOfDouble58(11)
arrayOfVariantOfDouble58(0) = 1.000000
arrayOfVariantOfDouble58(1) = 0.000000
arrayOfVariantOfDouble58(2) = 0.000000
arrayOfVariantOfDouble58(3) = 0.000000
arrayOfVariantOfDouble58(4) = 1.000000
arrayOfVariantOfDouble58(5) = 0.000000
arrayOfVariantOfDouble58(6) = 0.000000
arrayOfVariantOfDouble58(7) = 0.000000
arrayOfVariantOfDouble58(8) = 1.000000
arrayOfVariantOfDouble58(9) = -0.376577
arrayOfVariantOfDouble58(10) = 0.000000
arrayOfVariantOfDouble58(11) = 0.000000
move1.Apply arrayOfVariantOfDouble58

Set move1 = product3.Move

Set move1 = move1.MovableObject

Dim arrayOfVariantOfDouble59(11)
arrayOfVariantOfDouble59(0) = 1.000000
arrayOfVariantOfDouble59(1) = 0.000000
arrayOfVariantOfDouble59(2) = 0.000000
arrayOfVariantOfDouble59(3) = 0.000000
arrayOfVariantOfDouble59(4) = 1.000000
arrayOfVariantOfDouble59(5) = 0.000000
arrayOfVariantOfDouble59(6) = 0.000000
arrayOfVariantOfDouble59(7) = 0.000000
arrayOfVariantOfDouble59(8) = 1.000000
arrayOfVariantOfDouble59(9) = -0.376583
arrayOfVariantOfDouble59(10) = 0.000000
arrayOfVariantOfDouble59(11) = 0.000000
move1.Apply arrayOfVariantOfDouble59

Set move1 = product3.Move

Set move1 = move1.MovableObject

Dim arrayOfVariantOfDouble60(11)
arrayOfVariantOfDouble60(0) = 1.000000
arrayOfVariantOfDouble60(1) = 0.000000
arrayOfVariantOfDouble60(2) = 0.000000
arrayOfVariantOfDouble60(3) = 0.000000
arrayOfVariantOfDouble60(4) = 1.000000
arrayOfVariantOfDouble60(5) = 0.000000
arrayOfVariantOfDouble60(6) = 0.000000
arrayOfVariantOfDouble60(7) = 0.000000
arrayOfVariantOfDouble60(8) = 1.000000
arrayOfVariantOfDouble60(9) = -0.376586
arrayOfVariantOfDouble60(10) = 0.000000
arrayOfVariantOfDouble60(11) = 0.000000
move1.Apply arrayOfVariantOfDouble60

Set move1 = product3.Move

Set move1 = move1.MovableObject

Dim arrayOfVariantOfDouble61(11)
arrayOfVariantOfDouble61(0) = 1.000000
arrayOfVariantOfDouble61(1) = 0.000000
arrayOfVariantOfDouble61(2) = 0.000000
arrayOfVariantOfDouble61(3) = 0.000000
arrayOfVariantOfDouble61(4) = 1.000000
arrayOfVariantOfDouble61(5) = 0.000000
arrayOfVariantOfDouble61(6) = 0.000000
arrayOfVariantOfDouble61(7) = 0.000000
arrayOfVariantOfDouble61(8) = 1.000000
arrayOfVariantOfDouble61(9) = -0.376577
arrayOfVariantOfDouble61(10) = 0.000000
arrayOfVariantOfDouble61(11) = 0.000000
move1.Apply arrayOfVariantOfDouble61

Set move1 = product3.Move

Set move1 = move1.MovableObject

Dim arrayOfVariantOfDouble62(11)
arrayOfVariantOfDouble62(0) = 1.000000
arrayOfVariantOfDouble62(1) = 0.000000
arrayOfVariantOfDouble62(2) = 0.000000
arrayOfVariantOfDouble62(3) = 0.000000
arrayOfVariantOfDouble62(4) = 1.000000
arrayOfVariantOfDouble62(5) = 0.000000
arrayOfVariantOfDouble62(6) = 0.000000
arrayOfVariantOfDouble62(7) = 0.000000
arrayOfVariantOfDouble62(8) = 1.000000
arrayOfVariantOfDouble62(9) = -0.376578
arrayOfVariantOfDouble62(10) = 0.000000
arrayOfVariantOfDouble62(11) = 0.000000
move1.Apply arrayOfVariantOfDouble62

Set move1 = product3.Move

Set move1 = move1.MovableObject

Dim arrayOfVariantOfDouble63(11)
arrayOfVariantOfDouble63(0) = 1.000000
arrayOfVariantOfDouble63(1) = 0.000000
arrayOfVariantOfDouble63(2) = 0.000000
arrayOfVariantOfDouble63(3) = 0.000000
arrayOfVariantOfDouble63(4) = 1.000000
arrayOfVariantOfDouble63(5) = 0.000000
arrayOfVariantOfDouble63(6) = 0.000000
arrayOfVariantOfDouble63(7) = 0.000000
arrayOfVariantOfDouble63(8) = 1.000000
arrayOfVariantOfDouble63(9) = -0.376586
arrayOfVariantOfDouble63(10) = 0.000000
arrayOfVariantOfDouble63(11) = 0.000000
move1.Apply arrayOfVariantOfDouble63

Set move1 = product3.Move

Set move1 = move1.MovableObject

Dim arrayOfVariantOfDouble64(11)
arrayOfVariantOfDouble64(0) = 1.000000
arrayOfVariantOfDouble64(1) = 0.000000
arrayOfVariantOfDouble64(2) = 0.000000
arrayOfVariantOfDouble64(3) = 0.000000
arrayOfVariantOfDouble64(4) = 1.000000
arrayOfVariantOfDouble64(5) = 0.000000
arrayOfVariantOfDouble64(6) = 0.000000
arrayOfVariantOfDouble64(7) = 0.000000
arrayOfVariantOfDouble64(8) = 1.000000
arrayOfVariantOfDouble64(9) = -0.376579
arrayOfVariantOfDouble64(10) = 0.000000
arrayOfVariantOfDouble64(11) = 0.000000
move1.Apply arrayOfVariantOfDouble64

Set move1 = product3.Move

Set move1 = move1.MovableObject

Dim arrayOfVariantOfDouble65(11)
arrayOfVariantOfDouble65(0) = 1.000000
arrayOfVariantOfDouble65(1) = 0.000000
arrayOfVariantOfDouble65(2) = 0.000000
arrayOfVariantOfDouble65(3) = 0.000000
arrayOfVariantOfDouble65(4) = 1.000000
arrayOfVariantOfDouble65(5) = 0.000000
arrayOfVariantOfDouble65(6) = 0.000000
arrayOfVariantOfDouble65(7) = 0.000000
arrayOfVariantOfDouble65(8) = 1.000000
arrayOfVariantOfDouble65(9) = -0.376581
arrayOfVariantOfDouble65(10) = 0.000000
arrayOfVariantOfDouble65(11) = 0.000000
move1.Apply arrayOfVariantOfDouble65

Set move1 = product3.Move

Set move1 = move1.MovableObject

Dim arrayOfVariantOfDouble66(11)
arrayOfVariantOfDouble66(0) = 1.000000
arrayOfVariantOfDouble66(1) = 0.000000
arrayOfVariantOfDouble66(2) = 0.000000
arrayOfVariantOfDouble66(3) = 0.000000
arrayOfVariantOfDouble66(4) = 1.000000
arrayOfVariantOfDouble66(5) = 0.000000
arrayOfVariantOfDouble66(6) = 0.000000
arrayOfVariantOfDouble66(7) = 0.000000
arrayOfVariantOfDouble66(8) = 1.000000
arrayOfVariantOfDouble66(9) = -0.376578
arrayOfVariantOfDouble66(10) = 0.000000
arrayOfVariantOfDouble66(11) = 0.000000
move1.Apply arrayOfVariantOfDouble66

Set move1 = product3.Move

Set move1 = move1.MovableObject

Dim arrayOfVariantOfDouble67(11)
arrayOfVariantOfDouble67(0) = 1.000000
arrayOfVariantOfDouble67(1) = 0.000000
arrayOfVariantOfDouble67(2) = 0.000000
arrayOfVariantOfDouble67(3) = 0.000000
arrayOfVariantOfDouble67(4) = 1.000000
arrayOfVariantOfDouble67(5) = 0.000000
arrayOfVariantOfDouble67(6) = 0.000000
arrayOfVariantOfDouble67(7) = 0.000000
arrayOfVariantOfDouble67(8) = 1.000000
arrayOfVariantOfDouble67(9) = -0.376589
arrayOfVariantOfDouble67(10) = 0.000000
arrayOfVariantOfDouble67(11) = 0.000000
move1.Apply arrayOfVariantOfDouble67

Set move1 = product3.Move

Set move1 = move1.MovableObject

Dim arrayOfVariantOfDouble68(11)
arrayOfVariantOfDouble68(0) = 1.000000
arrayOfVariantOfDouble68(1) = 0.000000
arrayOfVariantOfDouble68(2) = 0.000000
arrayOfVariantOfDouble68(3) = 0.000000
arrayOfVariantOfDouble68(4) = 1.000000
arrayOfVariantOfDouble68(5) = 0.000000
arrayOfVariantOfDouble68(6) = 0.000000
arrayOfVariantOfDouble68(7) = 0.000000
arrayOfVariantOfDouble68(8) = 1.000000
arrayOfVariantOfDouble68(9) = -0.376578
arrayOfVariantOfDouble68(10) = 0.000000
arrayOfVariantOfDouble68(11) = 0.000000
move1.Apply arrayOfVariantOfDouble68

Set move1 = product3.Move

Set move1 = move1.MovableObject

Dim arrayOfVariantOfDouble69(11)
arrayOfVariantOfDouble69(0) = 1.000000
arrayOfVariantOfDouble69(1) = 0.000000
arrayOfVariantOfDouble69(2) = 0.000000
arrayOfVariantOfDouble69(3) = 0.000000
arrayOfVariantOfDouble69(4) = 1.000000
arrayOfVariantOfDouble69(5) = 0.000000
arrayOfVariantOfDouble69(6) = 0.000000
arrayOfVariantOfDouble69(7) = 0.000000
arrayOfVariantOfDouble69(8) = 1.000000
arrayOfVariantOfDouble69(9) = -0.376577
arrayOfVariantOfDouble69(10) = 0.000000
arrayOfVariantOfDouble69(11) = 0.000000
move1.Apply arrayOfVariantOfDouble69

Set move1 = product3.Move

Set move1 = move1.MovableObject

Dim arrayOfVariantOfDouble70(11)
arrayOfVariantOfDouble70(0) = 1.000000
arrayOfVariantOfDouble70(1) = 0.000000
arrayOfVariantOfDouble70(2) = 0.000000
arrayOfVariantOfDouble70(3) = 0.000000
arrayOfVariantOfDouble70(4) = 1.000000
arrayOfVariantOfDouble70(5) = 0.000000
arrayOfVariantOfDouble70(6) = 0.000000
arrayOfVariantOfDouble70(7) = 0.000000
arrayOfVariantOfDouble70(8) = 1.000000
arrayOfVariantOfDouble70(9) = -0.376585
arrayOfVariantOfDouble70(10) = 0.000000
arrayOfVariantOfDouble70(11) = 0.000000
move1.Apply arrayOfVariantOfDouble70

Set move1 = product3.Move

Set move1 = move1.MovableObject

Dim arrayOfVariantOfDouble71(11)
arrayOfVariantOfDouble71(0) = 1.000000
arrayOfVariantOfDouble71(1) = 0.000000
arrayOfVariantOfDouble71(2) = 0.000000
arrayOfVariantOfDouble71(3) = 0.000000
arrayOfVariantOfDouble71(4) = 1.000000
arrayOfVariantOfDouble71(5) = 0.000000
arrayOfVariantOfDouble71(6) = 0.000000
arrayOfVariantOfDouble71(7) = 0.000000
arrayOfVariantOfDouble71(8) = 1.000000
arrayOfVariantOfDouble71(9) = -0.753161
arrayOfVariantOfDouble71(10) = 0.000000
arrayOfVariantOfDouble71(11) = 0.000000
move1.Apply arrayOfVariantOfDouble71

Set move1 = product3.Move

Set move1 = move1.MovableObject

Dim arrayOfVariantOfDouble72(11)
arrayOfVariantOfDouble72(0) = 1.000000
arrayOfVariantOfDouble72(1) = 0.000000
arrayOfVariantOfDouble72(2) = 0.000000
arrayOfVariantOfDouble72(3) = 0.000000
arrayOfVariantOfDouble72(4) = 1.000000
arrayOfVariantOfDouble72(5) = 0.000000
arrayOfVariantOfDouble72(6) = 0.000000
arrayOfVariantOfDouble72(7) = 0.000000
arrayOfVariantOfDouble72(8) = 1.000000
arrayOfVariantOfDouble72(9) = -0.753165
arrayOfVariantOfDouble72(10) = 0.000000
arrayOfVariantOfDouble72(11) = 0.000000
move1.Apply arrayOfVariantOfDouble72

Set move1 = product3.Move

Set move1 = move1.MovableObject

Dim arrayOfVariantOfDouble73(11)
arrayOfVariantOfDouble73(0) = 1.000000
arrayOfVariantOfDouble73(1) = 0.000000
arrayOfVariantOfDouble73(2) = 0.000000
arrayOfVariantOfDouble73(3) = 0.000000
arrayOfVariantOfDouble73(4) = 1.000000
arrayOfVariantOfDouble73(5) = 0.000000
arrayOfVariantOfDouble73(6) = 0.000000
arrayOfVariantOfDouble73(7) = 0.000000
arrayOfVariantOfDouble73(8) = 1.000000
arrayOfVariantOfDouble73(9) = -0.376577
arrayOfVariantOfDouble73(10) = 0.000000
arrayOfVariantOfDouble73(11) = 0.000000
move1.Apply arrayOfVariantOfDouble73

Set move1 = product3.Move

Set move1 = move1.MovableObject

Dim arrayOfVariantOfDouble74(11)
arrayOfVariantOfDouble74(0) = 1.000000
arrayOfVariantOfDouble74(1) = 0.000000
arrayOfVariantOfDouble74(2) = 0.000000
arrayOfVariantOfDouble74(3) = 0.000000
arrayOfVariantOfDouble74(4) = 1.000000
arrayOfVariantOfDouble74(5) = 0.000000
arrayOfVariantOfDouble74(6) = 0.000000
arrayOfVariantOfDouble74(7) = 0.000000
arrayOfVariantOfDouble74(8) = 1.000000
arrayOfVariantOfDouble74(9) = -0.753168
arrayOfVariantOfDouble74(10) = 0.000000
arrayOfVariantOfDouble74(11) = 0.000000
move1.Apply arrayOfVariantOfDouble74

Set move1 = product3.Move

Set move1 = move1.MovableObject

Dim arrayOfVariantOfDouble75(11)
arrayOfVariantOfDouble75(0) = 1.000000
arrayOfVariantOfDouble75(1) = 0.000000
arrayOfVariantOfDouble75(2) = 0.000000
arrayOfVariantOfDouble75(3) = 0.000000
arrayOfVariantOfDouble75(4) = 1.000000
arrayOfVariantOfDouble75(5) = 0.000000
arrayOfVariantOfDouble75(6) = 0.000000
arrayOfVariantOfDouble75(7) = 0.000000
arrayOfVariantOfDouble75(8) = 1.000000
arrayOfVariantOfDouble75(9) = -0.753158
arrayOfVariantOfDouble75(10) = 0.000000
arrayOfVariantOfDouble75(11) = 0.000000
move1.Apply arrayOfVariantOfDouble75

Set move1 = product3.Move

Set move1 = move1.MovableObject

Dim arrayOfVariantOfDouble76(11)
arrayOfVariantOfDouble76(0) = 1.000000
arrayOfVariantOfDouble76(1) = 0.000000
arrayOfVariantOfDouble76(2) = 0.000000
arrayOfVariantOfDouble76(3) = 0.000000
arrayOfVariantOfDouble76(4) = 1.000000
arrayOfVariantOfDouble76(5) = 0.000000
arrayOfVariantOfDouble76(6) = 0.000000
arrayOfVariantOfDouble76(7) = 0.000000
arrayOfVariantOfDouble76(8) = 1.000000
arrayOfVariantOfDouble76(9) = -0.753165
arrayOfVariantOfDouble76(10) = 0.000000
arrayOfVariantOfDouble76(11) = 0.000000
move1.Apply arrayOfVariantOfDouble76

Set move1 = product3.Move

Set move1 = move1.MovableObject

Dim arrayOfVariantOfDouble77(11)
arrayOfVariantOfDouble77(0) = 1.000000
arrayOfVariantOfDouble77(1) = 0.000000
arrayOfVariantOfDouble77(2) = 0.000000
arrayOfVariantOfDouble77(3) = 0.000000
arrayOfVariantOfDouble77(4) = 1.000000
arrayOfVariantOfDouble77(5) = 0.000000
arrayOfVariantOfDouble77(6) = 0.000000
arrayOfVariantOfDouble77(7) = 0.000000
arrayOfVariantOfDouble77(8) = 1.000000
arrayOfVariantOfDouble77(9) = -1.129746
arrayOfVariantOfDouble77(10) = 0.000000
arrayOfVariantOfDouble77(11) = 0.000000
move1.Apply arrayOfVariantOfDouble77

Set move1 = product3.Move

Set move1 = move1.MovableObject

Dim arrayOfVariantOfDouble78(11)
arrayOfVariantOfDouble78(0) = 1.000000
arrayOfVariantOfDouble78(1) = 0.000000
arrayOfVariantOfDouble78(2) = 0.000000
arrayOfVariantOfDouble78(3) = 0.000000
arrayOfVariantOfDouble78(4) = 1.000000
arrayOfVariantOfDouble78(5) = 0.000000
arrayOfVariantOfDouble78(6) = 0.000000
arrayOfVariantOfDouble78(7) = 0.000000
arrayOfVariantOfDouble78(8) = 1.000000
arrayOfVariantOfDouble78(9) = -0.376578
arrayOfVariantOfDouble78(10) = 0.000000
arrayOfVariantOfDouble78(11) = 0.000000
move1.Apply arrayOfVariantOfDouble78

Set move1 = product3.Move

Set move1 = move1.MovableObject

Dim arrayOfVariantOfDouble79(11)
arrayOfVariantOfDouble79(0) = 1.000000
arrayOfVariantOfDouble79(1) = 0.000000
arrayOfVariantOfDouble79(2) = 0.000000
arrayOfVariantOfDouble79(3) = 0.000000
arrayOfVariantOfDouble79(4) = 1.000000
arrayOfVariantOfDouble79(5) = 0.000000
arrayOfVariantOfDouble79(6) = 0.000000
arrayOfVariantOfDouble79(7) = 0.000000
arrayOfVariantOfDouble79(8) = 1.000000
arrayOfVariantOfDouble79(9) = -0.753165
arrayOfVariantOfDouble79(10) = 0.000000
arrayOfVariantOfDouble79(11) = 0.000000
move1.Apply arrayOfVariantOfDouble79

Set move1 = product3.Move

Set move1 = move1.MovableObject

Dim arrayOfVariantOfDouble80(11)
arrayOfVariantOfDouble80(0) = 1.000000
arrayOfVariantOfDouble80(1) = 0.000000
arrayOfVariantOfDouble80(2) = 0.000000
arrayOfVariantOfDouble80(3) = 0.000000
arrayOfVariantOfDouble80(4) = 1.000000
arrayOfVariantOfDouble80(5) = 0.000000
arrayOfVariantOfDouble80(6) = 0.000000
arrayOfVariantOfDouble80(7) = 0.000000
arrayOfVariantOfDouble80(8) = 1.000000
arrayOfVariantOfDouble80(9) = -0.753156
arrayOfVariantOfDouble80(10) = 0.000000
arrayOfVariantOfDouble80(11) = 0.000000
move1.Apply arrayOfVariantOfDouble80

Set move1 = product3.Move

Set move1 = move1.MovableObject

Dim arrayOfVariantOfDouble81(11)
arrayOfVariantOfDouble81(0) = 1.000000
arrayOfVariantOfDouble81(1) = 0.000000
arrayOfVariantOfDouble81(2) = 0.000000
arrayOfVariantOfDouble81(3) = 0.000000
arrayOfVariantOfDouble81(4) = 1.000000
arrayOfVariantOfDouble81(5) = 0.000000
arrayOfVariantOfDouble81(6) = 0.000000
arrayOfVariantOfDouble81(7) = 0.000000
arrayOfVariantOfDouble81(8) = 1.000000
arrayOfVariantOfDouble81(9) = -0.753167
arrayOfVariantOfDouble81(10) = 0.000000
arrayOfVariantOfDouble81(11) = 0.000000
move1.Apply arrayOfVariantOfDouble81

Set move1 = product3.Move

Set move1 = move1.MovableObject

Dim arrayOfVariantOfDouble82(11)
arrayOfVariantOfDouble82(0) = 1.000000
arrayOfVariantOfDouble82(1) = 0.000000
arrayOfVariantOfDouble82(2) = 0.000000
arrayOfVariantOfDouble82(3) = 0.000000
arrayOfVariantOfDouble82(4) = 1.000000
arrayOfVariantOfDouble82(5) = 0.000000
arrayOfVariantOfDouble82(6) = 0.000000
arrayOfVariantOfDouble82(7) = 0.000000
arrayOfVariantOfDouble82(8) = 1.000000
arrayOfVariantOfDouble82(9) = -0.753156
arrayOfVariantOfDouble82(10) = 0.000000
arrayOfVariantOfDouble82(11) = 0.000000
move1.Apply arrayOfVariantOfDouble82

Set move1 = product3.Move

Set move1 = move1.MovableObject

Dim arrayOfVariantOfDouble83(11)
arrayOfVariantOfDouble83(0) = 1.000000
arrayOfVariantOfDouble83(1) = 0.000000
arrayOfVariantOfDouble83(2) = 0.000000
arrayOfVariantOfDouble83(3) = 0.000000
arrayOfVariantOfDouble83(4) = 1.000000
arrayOfVariantOfDouble83(5) = 0.000000
arrayOfVariantOfDouble83(6) = 0.000000
arrayOfVariantOfDouble83(7) = 0.000000
arrayOfVariantOfDouble83(8) = 1.000000
arrayOfVariantOfDouble83(9) = -0.753166
arrayOfVariantOfDouble83(10) = 0.000000
arrayOfVariantOfDouble83(11) = 0.000000
move1.Apply arrayOfVariantOfDouble83

Set move1 = product3.Move

Set move1 = move1.MovableObject

Dim arrayOfVariantOfDouble84(11)
arrayOfVariantOfDouble84(0) = 1.000000
arrayOfVariantOfDouble84(1) = 0.000000
arrayOfVariantOfDouble84(2) = 0.000000
arrayOfVariantOfDouble84(3) = 0.000000
arrayOfVariantOfDouble84(4) = 1.000000
arrayOfVariantOfDouble84(5) = 0.000000
arrayOfVariantOfDouble84(6) = 0.000000
arrayOfVariantOfDouble84(7) = 0.000000
arrayOfVariantOfDouble84(8) = 1.000000
arrayOfVariantOfDouble84(9) = -0.376581
arrayOfVariantOfDouble84(10) = 0.000000
arrayOfVariantOfDouble84(11) = 0.000000
move1.Apply arrayOfVariantOfDouble84

Set move1 = product3.Move

Set move1 = move1.MovableObject

Dim arrayOfVariantOfDouble85(11)
arrayOfVariantOfDouble85(0) = 1.000000
arrayOfVariantOfDouble85(1) = 0.000000
arrayOfVariantOfDouble85(2) = 0.000000
arrayOfVariantOfDouble85(3) = 0.000000
arrayOfVariantOfDouble85(4) = 1.000000
arrayOfVariantOfDouble85(5) = 0.000000
arrayOfVariantOfDouble85(6) = 0.000000
arrayOfVariantOfDouble85(7) = 0.000000
arrayOfVariantOfDouble85(8) = 1.000000
arrayOfVariantOfDouble85(9) = -0.376588
arrayOfVariantOfDouble85(10) = 0.000000
arrayOfVariantOfDouble85(11) = 0.000000
move1.Apply arrayOfVariantOfDouble85

Set move1 = product3.Move

Set move1 = move1.MovableObject

Dim arrayOfVariantOfDouble86(11)
arrayOfVariantOfDouble86(0) = 1.000000
arrayOfVariantOfDouble86(1) = 0.000000
arrayOfVariantOfDouble86(2) = 0.000000
arrayOfVariantOfDouble86(3) = 0.000000
arrayOfVariantOfDouble86(4) = 1.000000
arrayOfVariantOfDouble86(5) = 0.000000
arrayOfVariantOfDouble86(6) = 0.000000
arrayOfVariantOfDouble86(7) = 0.000000
arrayOfVariantOfDouble86(8) = 1.000000
arrayOfVariantOfDouble86(9) = -0.376578
arrayOfVariantOfDouble86(10) = 0.000000
arrayOfVariantOfDouble86(11) = 0.000000
move1.Apply arrayOfVariantOfDouble86

Set constraints1 = product1.Connections("CATIAConstraints")

Dim reference18 As Reference
Set reference18 = product1.CreateReferenceFromName("A2/Nut.1/!Axis:(Selection_RSur:(Face:(Brp:(Pocket.1;0:(Brp:(Sketch.2;4)));None:();Cf11:());Pocket.1_ResultOUT;Z0;G4162))")

Dim reference19 As Reference
Set reference19 = product1.CreateReferenceFromName("A2/DM.2/!Axis:(Selection_RSur:(Face:(Brp:(Pocket.1;0:(Brp:(Sketch.2;4)));None:();Cf11:());Pocket.2_ResultOUT;Z0;G4162))")

Dim constraint11 As Constraint
Set constraint11 = constraints1.AddBiEltCst(catCstTypeOn, reference18, reference19)

Set constraints1 = product1.Connections("CATIAConstraints")

Dim reference20 As Reference
Set reference20 = product1.CreateReferenceFromName("A2/Nut.1/!Selection_RSur:(Face:(Brp:(Pad.1;2);None:();Cf11:());Pocket.1_ResultOUT;Z0;G4162)")

Dim reference21 As Reference
Set reference21 = product1.CreateReferenceFromName("A2/DM.2/!Selection_RSur:(Face:(Brp:(Pad.1;0:(Brp:(Sketch.1;13)));None:();Cf11:());Pocket.2_ResultOUT;Z0;G4162)")

Dim constraint12 As Constraint
Set constraint12 = constraints1.AddBiEltCst(catCstTypeSurfContact, reference20, reference21)

product1.Update 

Set product1 = product1.ReferenceProduct

Set constraints1 = product1.Connections("CATIAConstraints")

Dim reference22 As Reference
Set reference22 = product1.CreateReferenceFromName("A2/Nut.1/!Selection_RSur:(Face:(Brp:(Pad.1;0:(Brp:(Sketch.1;8)));None:();Cf11:());Pocket.1_ResultOUT;Z0;G4162)")

Dim reference23 As Reference
Set reference23 = product1.CreateReferenceFromName("A2/DM.2/!Selection_RSur:(Face:(Brp:(Pad.1;0:(Brp:(Sketch.1;12)));None:();Cf11:());Pocket.2_ResultOUT;Z0;G4162)")

Dim constraint13 As Constraint
Set constraint13 = constraints1.AddBiEltCst(catCstTypeAngle, reference22, reference23)

Dim angle1 As Dimension
Set angle1 = constraint13.Dimension

angle1.Value = 0.000000

constraint13.AngleSector = catCstAngleSector0

product1.Update 

Dim arrayOfVariantOfBSTR6(0)
arrayOfVariantOfBSTR6(0) = ".\SubAssembly\Nut.CATPart"
products1.AddComponentsFromFiles arrayOfVariantOfBSTR6, "All"

Dim product4 As Product
Set product4 = products1.Item("Nut.2")

Dim move2 As Move
Set move2 = product4.Move

Set move2 = move2.MovableObject

Dim arrayOfVariantOfDouble87(11)
arrayOfVariantOfDouble87(0) = 1.000000
arrayOfVariantOfDouble87(1) = 0.000000
arrayOfVariantOfDouble87(2) = 0.000000
arrayOfVariantOfDouble87(3) = 0.000000
arrayOfVariantOfDouble87(4) = 1.000000
arrayOfVariantOfDouble87(5) = 0.000000
arrayOfVariantOfDouble87(6) = 0.000000
arrayOfVariantOfDouble87(7) = 0.000000
arrayOfVariantOfDouble87(8) = 1.000000
arrayOfVariantOfDouble87(9) = 6.229100
arrayOfVariantOfDouble87(10) = 0.000000
arrayOfVariantOfDouble87(11) = 0.000000
move2.Apply arrayOfVariantOfDouble87

Set move2 = product4.Move

Set move2 = move2.MovableObject

Dim arrayOfVariantOfDouble88(11)
arrayOfVariantOfDouble88(0) = 1.000000
arrayOfVariantOfDouble88(1) = 0.000000
arrayOfVariantOfDouble88(2) = 0.000000
arrayOfVariantOfDouble88(3) = 0.000000
arrayOfVariantOfDouble88(4) = 1.000000
arrayOfVariantOfDouble88(5) = 0.000000
arrayOfVariantOfDouble88(6) = 0.000000
arrayOfVariantOfDouble88(7) = 0.000000
arrayOfVariantOfDouble88(8) = 1.000000
arrayOfVariantOfDouble88(9) = 1.166967
arrayOfVariantOfDouble88(10) = 0.000000
arrayOfVariantOfDouble88(11) = 0.000000
move2.Apply arrayOfVariantOfDouble88

Set move2 = product4.Move

Set move2 = move2.MovableObject

Dim arrayOfVariantOfDouble89(11)
arrayOfVariantOfDouble89(0) = 1.000000
arrayOfVariantOfDouble89(1) = 0.000000
arrayOfVariantOfDouble89(2) = 0.000000
arrayOfVariantOfDouble89(3) = 0.000000
arrayOfVariantOfDouble89(4) = 1.000000
arrayOfVariantOfDouble89(5) = 0.000000
arrayOfVariantOfDouble89(6) = 0.000000
arrayOfVariantOfDouble89(7) = 0.000000
arrayOfVariantOfDouble89(8) = 1.000000
arrayOfVariantOfDouble89(9) = 0.583480
arrayOfVariantOfDouble89(10) = 0.000000
arrayOfVariantOfDouble89(11) = 0.000000
move2.Apply arrayOfVariantOfDouble89

Set move2 = product4.Move

Set move2 = move2.MovableObject

Dim arrayOfVariantOfDouble90(11)
arrayOfVariantOfDouble90(0) = 1.000000
arrayOfVariantOfDouble90(1) = 0.000000
arrayOfVariantOfDouble90(2) = 0.000000
arrayOfVariantOfDouble90(3) = 0.000000
arrayOfVariantOfDouble90(4) = 1.000000
arrayOfVariantOfDouble90(5) = 0.000000
arrayOfVariantOfDouble90(6) = 0.000000
arrayOfVariantOfDouble90(7) = 0.000000
arrayOfVariantOfDouble90(8) = 1.000000
arrayOfVariantOfDouble90(9) = 0.488175
arrayOfVariantOfDouble90(10) = 0.000000
arrayOfVariantOfDouble90(11) = 0.000000
move2.Apply arrayOfVariantOfDouble90

Set move2 = product4.Move

Set move2 = move2.MovableObject

Dim arrayOfVariantOfDouble91(11)
arrayOfVariantOfDouble91(0) = 1.000000
arrayOfVariantOfDouble91(1) = 0.000000
arrayOfVariantOfDouble91(2) = 0.000000
arrayOfVariantOfDouble91(3) = 0.000000
arrayOfVariantOfDouble91(4) = 1.000000
arrayOfVariantOfDouble91(5) = 0.000000
arrayOfVariantOfDouble91(6) = 0.000000
arrayOfVariantOfDouble91(7) = 0.000000
arrayOfVariantOfDouble91(8) = 1.000000
arrayOfVariantOfDouble91(9) = 1.166969
arrayOfVariantOfDouble91(10) = 0.000000
arrayOfVariantOfDouble91(11) = 0.000000
move2.Apply arrayOfVariantOfDouble91

Set move2 = product4.Move

Set move2 = move2.MovableObject

Dim arrayOfVariantOfDouble92(11)
arrayOfVariantOfDouble92(0) = 1.000000
arrayOfVariantOfDouble92(1) = 0.000000
arrayOfVariantOfDouble92(2) = 0.000000
arrayOfVariantOfDouble92(3) = 0.000000
arrayOfVariantOfDouble92(4) = 1.000000
arrayOfVariantOfDouble92(5) = 0.000000
arrayOfVariantOfDouble92(6) = 0.000000
arrayOfVariantOfDouble92(7) = 0.000000
arrayOfVariantOfDouble92(8) = 1.000000
arrayOfVariantOfDouble92(9) = 0.583489
arrayOfVariantOfDouble92(10) = 0.000000
arrayOfVariantOfDouble92(11) = 0.000000
move2.Apply arrayOfVariantOfDouble92

Set move2 = product4.Move

Set move2 = move2.MovableObject

Dim arrayOfVariantOfDouble93(11)
arrayOfVariantOfDouble93(0) = 1.000000
arrayOfVariantOfDouble93(1) = 0.000000
arrayOfVariantOfDouble93(2) = 0.000000
arrayOfVariantOfDouble93(3) = 0.000000
arrayOfVariantOfDouble93(4) = 1.000000
arrayOfVariantOfDouble93(5) = 0.000000
arrayOfVariantOfDouble93(6) = 0.000000
arrayOfVariantOfDouble93(7) = 0.000000
arrayOfVariantOfDouble93(8) = 1.000000
arrayOfVariantOfDouble93(9) = 0.583487
arrayOfVariantOfDouble93(10) = 0.000000
arrayOfVariantOfDouble93(11) = 0.000000
move2.Apply arrayOfVariantOfDouble93

Set move2 = product4.Move

Set move2 = move2.MovableObject

Dim arrayOfVariantOfDouble94(11)
arrayOfVariantOfDouble94(0) = 1.000000
arrayOfVariantOfDouble94(1) = 0.000000
arrayOfVariantOfDouble94(2) = 0.000000
arrayOfVariantOfDouble94(3) = 0.000000
arrayOfVariantOfDouble94(4) = 1.000000
arrayOfVariantOfDouble94(5) = 0.000000
arrayOfVariantOfDouble94(6) = 0.000000
arrayOfVariantOfDouble94(7) = 0.000000
arrayOfVariantOfDouble94(8) = 1.000000
arrayOfVariantOfDouble94(9) = 1.166968
arrayOfVariantOfDouble94(10) = 0.000000
arrayOfVariantOfDouble94(11) = 0.000000
move2.Apply arrayOfVariantOfDouble94

Set move2 = product4.Move

Set move2 = move2.MovableObject

Dim arrayOfVariantOfDouble95(11)
arrayOfVariantOfDouble95(0) = 1.000000
arrayOfVariantOfDouble95(1) = 0.000000
arrayOfVariantOfDouble95(2) = 0.000000
arrayOfVariantOfDouble95(3) = 0.000000
arrayOfVariantOfDouble95(4) = 1.000000
arrayOfVariantOfDouble95(5) = 0.000000
arrayOfVariantOfDouble95(6) = 0.000000
arrayOfVariantOfDouble95(7) = 0.000000
arrayOfVariantOfDouble95(8) = 1.000000
arrayOfVariantOfDouble95(9) = 1.166969
arrayOfVariantOfDouble95(10) = 0.000000
arrayOfVariantOfDouble95(11) = 0.000000
move2.Apply arrayOfVariantOfDouble95

Set move2 = product4.Move

Set move2 = move2.MovableObject

Dim arrayOfVariantOfDouble96(11)
arrayOfVariantOfDouble96(0) = 1.000000
arrayOfVariantOfDouble96(1) = 0.000000
arrayOfVariantOfDouble96(2) = 0.000000
arrayOfVariantOfDouble96(3) = 0.000000
arrayOfVariantOfDouble96(4) = 1.000000
arrayOfVariantOfDouble96(5) = 0.000000
arrayOfVariantOfDouble96(6) = 0.000000
arrayOfVariantOfDouble96(7) = 0.000000
arrayOfVariantOfDouble96(8) = 1.000000
arrayOfVariantOfDouble96(9) = 1.166967
arrayOfVariantOfDouble96(10) = 0.000000
arrayOfVariantOfDouble96(11) = 0.000000
move2.Apply arrayOfVariantOfDouble96

Set move2 = product4.Move

Set move2 = move2.MovableObject

Dim arrayOfVariantOfDouble97(11)
arrayOfVariantOfDouble97(0) = 1.000000
arrayOfVariantOfDouble97(1) = 0.000000
arrayOfVariantOfDouble97(2) = 0.000000
arrayOfVariantOfDouble97(3) = 0.000000
arrayOfVariantOfDouble97(4) = 1.000000
arrayOfVariantOfDouble97(5) = 0.000000
arrayOfVariantOfDouble97(6) = 0.000000
arrayOfVariantOfDouble97(7) = 0.000000
arrayOfVariantOfDouble97(8) = 1.000000
arrayOfVariantOfDouble97(9) = 2.429259
arrayOfVariantOfDouble97(10) = 0.000000
arrayOfVariantOfDouble97(11) = 0.000000
move2.Apply arrayOfVariantOfDouble97

Set move2 = product4.Move

Set move2 = move2.MovableObject

Dim arrayOfVariantOfDouble98(11)
arrayOfVariantOfDouble98(0) = 1.000000
arrayOfVariantOfDouble98(1) = 0.000000
arrayOfVariantOfDouble98(2) = 0.000000
arrayOfVariantOfDouble98(3) = 0.000000
arrayOfVariantOfDouble98(4) = 1.000000
arrayOfVariantOfDouble98(5) = 0.000000
arrayOfVariantOfDouble98(6) = 0.000000
arrayOfVariantOfDouble98(7) = 0.000000
arrayOfVariantOfDouble98(8) = 1.000000
arrayOfVariantOfDouble98(9) = 0.583481
arrayOfVariantOfDouble98(10) = 0.000000
arrayOfVariantOfDouble98(11) = 0.000000
move2.Apply arrayOfVariantOfDouble98

Set move2 = product4.Move

Set move2 = move2.MovableObject

Dim arrayOfVariantOfDouble99(11)
arrayOfVariantOfDouble99(0) = 1.000000
arrayOfVariantOfDouble99(1) = 0.000000
arrayOfVariantOfDouble99(2) = 0.000000
arrayOfVariantOfDouble99(3) = 0.000000
arrayOfVariantOfDouble99(4) = 1.000000
arrayOfVariantOfDouble99(5) = 0.000000
arrayOfVariantOfDouble99(6) = 0.000000
arrayOfVariantOfDouble99(7) = 0.000000
arrayOfVariantOfDouble99(8) = 1.000000
arrayOfVariantOfDouble99(9) = 2.429256
arrayOfVariantOfDouble99(10) = 0.000000
arrayOfVariantOfDouble99(11) = 0.000000
move2.Apply arrayOfVariantOfDouble99

Set move2 = product4.Move

Set move2 = move2.MovableObject

Dim arrayOfVariantOfDouble100(11)
arrayOfVariantOfDouble100(0) = 1.000000
arrayOfVariantOfDouble100(1) = 0.000000
arrayOfVariantOfDouble100(2) = 0.000000
arrayOfVariantOfDouble100(3) = 0.000000
arrayOfVariantOfDouble100(4) = 1.000000
arrayOfVariantOfDouble100(5) = 0.000000
arrayOfVariantOfDouble100(6) = 0.000000
arrayOfVariantOfDouble100(7) = 0.000000
arrayOfVariantOfDouble100(8) = 1.000000
arrayOfVariantOfDouble100(9) = 1.166970
arrayOfVariantOfDouble100(10) = 0.000000
arrayOfVariantOfDouble100(11) = 0.000000
move2.Apply arrayOfVariantOfDouble100

Set move2 = product4.Move

Set move2 = move2.MovableObject

Dim arrayOfVariantOfDouble101(11)
arrayOfVariantOfDouble101(0) = 1.000000
arrayOfVariantOfDouble101(1) = 0.000000
arrayOfVariantOfDouble101(2) = 0.000000
arrayOfVariantOfDouble101(3) = 0.000000
arrayOfVariantOfDouble101(4) = 1.000000
arrayOfVariantOfDouble101(5) = 0.000000
arrayOfVariantOfDouble101(6) = 0.000000
arrayOfVariantOfDouble101(7) = 0.000000
arrayOfVariantOfDouble101(8) = 1.000000
arrayOfVariantOfDouble101(9) = 1.845769
arrayOfVariantOfDouble101(10) = 0.000000
arrayOfVariantOfDouble101(11) = 0.000000
move2.Apply arrayOfVariantOfDouble101

Set move2 = product4.Move

Set move2 = move2.MovableObject

Dim arrayOfVariantOfDouble102(11)
arrayOfVariantOfDouble102(0) = 1.000000
arrayOfVariantOfDouble102(1) = 0.000000
arrayOfVariantOfDouble102(2) = 0.000000
arrayOfVariantOfDouble102(3) = 0.000000
arrayOfVariantOfDouble102(4) = 1.000000
arrayOfVariantOfDouble102(5) = 0.000000
arrayOfVariantOfDouble102(6) = 0.000000
arrayOfVariantOfDouble102(7) = 0.000000
arrayOfVariantOfDouble102(8) = 1.000000
arrayOfVariantOfDouble102(9) = 1.750456
arrayOfVariantOfDouble102(10) = 0.000000
arrayOfVariantOfDouble102(11) = 0.000000
move2.Apply arrayOfVariantOfDouble102

Set move2 = product4.Move

Set move2 = move2.MovableObject

Dim arrayOfVariantOfDouble103(11)
arrayOfVariantOfDouble103(0) = 1.000000
arrayOfVariantOfDouble103(1) = 0.000000
arrayOfVariantOfDouble103(2) = 0.000000
arrayOfVariantOfDouble103(3) = 0.000000
arrayOfVariantOfDouble103(4) = 1.000000
arrayOfVariantOfDouble103(5) = 0.000000
arrayOfVariantOfDouble103(6) = 0.000000
arrayOfVariantOfDouble103(7) = 0.000000
arrayOfVariantOfDouble103(8) = 1.000000
arrayOfVariantOfDouble103(9) = 1.166968
arrayOfVariantOfDouble103(10) = 0.000000
arrayOfVariantOfDouble103(11) = 0.000000
move2.Apply arrayOfVariantOfDouble103

Set move2 = product4.Move

Set move2 = move2.MovableObject

Dim arrayOfVariantOfDouble104(11)
arrayOfVariantOfDouble104(0) = 1.000000
arrayOfVariantOfDouble104(1) = 0.000000
arrayOfVariantOfDouble104(2) = 0.000000
arrayOfVariantOfDouble104(3) = 0.000000
arrayOfVariantOfDouble104(4) = 1.000000
arrayOfVariantOfDouble104(5) = 0.000000
arrayOfVariantOfDouble104(6) = 0.000000
arrayOfVariantOfDouble104(7) = 0.000000
arrayOfVariantOfDouble104(8) = 1.000000
arrayOfVariantOfDouble104(9) = 1.166968
arrayOfVariantOfDouble104(10) = 0.000000
arrayOfVariantOfDouble104(11) = 0.000000
move2.Apply arrayOfVariantOfDouble104

Set move2 = product4.Move

Set move2 = move2.MovableObject

Dim arrayOfVariantOfDouble105(11)
arrayOfVariantOfDouble105(0) = 1.000000
arrayOfVariantOfDouble105(1) = 0.000000
arrayOfVariantOfDouble105(2) = 0.000000
arrayOfVariantOfDouble105(3) = 0.000000
arrayOfVariantOfDouble105(4) = 1.000000
arrayOfVariantOfDouble105(5) = 0.000000
arrayOfVariantOfDouble105(6) = 0.000000
arrayOfVariantOfDouble105(7) = 0.000000
arrayOfVariantOfDouble105(8) = 1.000000
arrayOfVariantOfDouble105(9) = 1.845771
arrayOfVariantOfDouble105(10) = 0.000000
arrayOfVariantOfDouble105(11) = 0.000000
move2.Apply arrayOfVariantOfDouble105

Set move2 = product4.Move

Set move2 = move2.MovableObject

Dim arrayOfVariantOfDouble106(11)
arrayOfVariantOfDouble106(0) = 1.000000
arrayOfVariantOfDouble106(1) = 0.000000
arrayOfVariantOfDouble106(2) = 0.000000
arrayOfVariantOfDouble106(3) = 0.000000
arrayOfVariantOfDouble106(4) = 1.000000
arrayOfVariantOfDouble106(5) = 0.000000
arrayOfVariantOfDouble106(6) = 0.000000
arrayOfVariantOfDouble106(7) = 0.000000
arrayOfVariantOfDouble106(8) = 1.000000
arrayOfVariantOfDouble106(9) = 1.166969
arrayOfVariantOfDouble106(10) = 0.000000
arrayOfVariantOfDouble106(11) = 0.000000
move2.Apply arrayOfVariantOfDouble106

Set move2 = product4.Move

Set move2 = move2.MovableObject

Dim arrayOfVariantOfDouble107(11)
arrayOfVariantOfDouble107(0) = 1.000000
arrayOfVariantOfDouble107(1) = 0.000000
arrayOfVariantOfDouble107(2) = 0.000000
arrayOfVariantOfDouble107(3) = 0.000000
arrayOfVariantOfDouble107(4) = 1.000000
arrayOfVariantOfDouble107(5) = 0.000000
arrayOfVariantOfDouble107(6) = 0.000000
arrayOfVariantOfDouble107(7) = 0.000000
arrayOfVariantOfDouble107(8) = 1.000000
arrayOfVariantOfDouble107(9) = 1.166974
arrayOfVariantOfDouble107(10) = 0.000000
arrayOfVariantOfDouble107(11) = 0.000000
move2.Apply arrayOfVariantOfDouble107

Set move2 = product4.Move

Set move2 = move2.MovableObject

Dim arrayOfVariantOfDouble108(11)
arrayOfVariantOfDouble108(0) = 1.000000
arrayOfVariantOfDouble108(1) = 0.000000
arrayOfVariantOfDouble108(2) = 0.000000
arrayOfVariantOfDouble108(3) = 0.000000
arrayOfVariantOfDouble108(4) = 1.000000
arrayOfVariantOfDouble108(5) = 0.000000
arrayOfVariantOfDouble108(6) = 0.000000
arrayOfVariantOfDouble108(7) = 0.000000
arrayOfVariantOfDouble108(8) = 1.000000
arrayOfVariantOfDouble108(9) = 1.166970
arrayOfVariantOfDouble108(10) = 0.000000
arrayOfVariantOfDouble108(11) = 0.000000
move2.Apply arrayOfVariantOfDouble108

Set move2 = product4.Move

Set move2 = move2.MovableObject

Dim arrayOfVariantOfDouble109(11)
arrayOfVariantOfDouble109(0) = 1.000000
arrayOfVariantOfDouble109(1) = 0.000000
arrayOfVariantOfDouble109(2) = 0.000000
arrayOfVariantOfDouble109(3) = 0.000000
arrayOfVariantOfDouble109(4) = 1.000000
arrayOfVariantOfDouble109(5) = 0.000000
arrayOfVariantOfDouble109(6) = 0.000000
arrayOfVariantOfDouble109(7) = 0.000000
arrayOfVariantOfDouble109(8) = 1.000000
arrayOfVariantOfDouble109(9) = 1.166967
arrayOfVariantOfDouble109(10) = 0.000000
arrayOfVariantOfDouble109(11) = 0.000000
move2.Apply arrayOfVariantOfDouble109

Set move2 = product4.Move

Set move2 = move2.MovableObject

Dim arrayOfVariantOfDouble110(11)
arrayOfVariantOfDouble110(0) = 1.000000
arrayOfVariantOfDouble110(1) = 0.000000
arrayOfVariantOfDouble110(2) = 0.000000
arrayOfVariantOfDouble110(3) = 0.000000
arrayOfVariantOfDouble110(4) = 1.000000
arrayOfVariantOfDouble110(5) = 0.000000
arrayOfVariantOfDouble110(6) = 0.000000
arrayOfVariantOfDouble110(7) = 0.000000
arrayOfVariantOfDouble110(8) = 1.000000
arrayOfVariantOfDouble110(9) = 1.845770
arrayOfVariantOfDouble110(10) = 0.000000
arrayOfVariantOfDouble110(11) = 0.000000
move2.Apply arrayOfVariantOfDouble110

Set move2 = product4.Move

Set move2 = move2.MovableObject

Dim arrayOfVariantOfDouble111(11)
arrayOfVariantOfDouble111(0) = 1.000000
arrayOfVariantOfDouble111(1) = 0.000000
arrayOfVariantOfDouble111(2) = 0.000000
arrayOfVariantOfDouble111(3) = 0.000000
arrayOfVariantOfDouble111(4) = 1.000000
arrayOfVariantOfDouble111(5) = 0.000000
arrayOfVariantOfDouble111(6) = 0.000000
arrayOfVariantOfDouble111(7) = 0.000000
arrayOfVariantOfDouble111(8) = 1.000000
arrayOfVariantOfDouble111(9) = 1.166970
arrayOfVariantOfDouble111(10) = 0.000000
arrayOfVariantOfDouble111(11) = 0.000000
move2.Apply arrayOfVariantOfDouble111

Set move2 = product4.Move

Set move2 = move2.MovableObject

Dim arrayOfVariantOfDouble112(11)
arrayOfVariantOfDouble112(0) = 1.000000
arrayOfVariantOfDouble112(1) = 0.000000
arrayOfVariantOfDouble112(2) = 0.000000
arrayOfVariantOfDouble112(3) = 0.000000
arrayOfVariantOfDouble112(4) = 1.000000
arrayOfVariantOfDouble112(5) = 0.000000
arrayOfVariantOfDouble112(6) = 0.000000
arrayOfVariantOfDouble112(7) = 0.000000
arrayOfVariantOfDouble112(8) = 1.000000
arrayOfVariantOfDouble112(9) = 1.166967
arrayOfVariantOfDouble112(10) = 0.000000
arrayOfVariantOfDouble112(11) = 0.000000
move2.Apply arrayOfVariantOfDouble112

Set move2 = product4.Move

Set move2 = move2.MovableObject

Dim arrayOfVariantOfDouble113(11)
arrayOfVariantOfDouble113(0) = 1.000000
arrayOfVariantOfDouble113(1) = 0.000000
arrayOfVariantOfDouble113(2) = 0.000000
arrayOfVariantOfDouble113(3) = 0.000000
arrayOfVariantOfDouble113(4) = 1.000000
arrayOfVariantOfDouble113(5) = 0.000000
arrayOfVariantOfDouble113(6) = 0.000000
arrayOfVariantOfDouble113(7) = 0.000000
arrayOfVariantOfDouble113(8) = 1.000000
arrayOfVariantOfDouble113(9) = 1.166978
arrayOfVariantOfDouble113(10) = 0.000000
arrayOfVariantOfDouble113(11) = 0.000000
move2.Apply arrayOfVariantOfDouble113

Set move2 = product4.Move

Set move2 = move2.MovableObject

Dim arrayOfVariantOfDouble114(11)
arrayOfVariantOfDouble114(0) = 1.000000
arrayOfVariantOfDouble114(1) = 0.000000
arrayOfVariantOfDouble114(2) = 0.000000
arrayOfVariantOfDouble114(3) = 0.000000
arrayOfVariantOfDouble114(4) = 1.000000
arrayOfVariantOfDouble114(5) = 0.000000
arrayOfVariantOfDouble114(6) = 0.000000
arrayOfVariantOfDouble114(7) = 0.000000
arrayOfVariantOfDouble114(8) = 1.000000
arrayOfVariantOfDouble114(9) = 0.678792
arrayOfVariantOfDouble114(10) = 0.000000
arrayOfVariantOfDouble114(11) = 0.000000
move2.Apply arrayOfVariantOfDouble114

Set move2 = product4.Move

Set move2 = move2.MovableObject

Dim arrayOfVariantOfDouble115(11)
arrayOfVariantOfDouble115(0) = 1.000000
arrayOfVariantOfDouble115(1) = 0.000000
arrayOfVariantOfDouble115(2) = 0.000000
arrayOfVariantOfDouble115(3) = 0.000000
arrayOfVariantOfDouble115(4) = 1.000000
arrayOfVariantOfDouble115(5) = 0.000000
arrayOfVariantOfDouble115(6) = 0.000000
arrayOfVariantOfDouble115(7) = 0.000000
arrayOfVariantOfDouble115(8) = 1.000000
arrayOfVariantOfDouble115(9) = 1.750457
arrayOfVariantOfDouble115(10) = 0.000000
arrayOfVariantOfDouble115(11) = 0.000000
move2.Apply arrayOfVariantOfDouble115

Set move2 = product4.Move

Set move2 = move2.MovableObject

Dim arrayOfVariantOfDouble116(11)
arrayOfVariantOfDouble116(0) = 1.000000
arrayOfVariantOfDouble116(1) = 0.000000
arrayOfVariantOfDouble116(2) = 0.000000
arrayOfVariantOfDouble116(3) = 0.000000
arrayOfVariantOfDouble116(4) = 1.000000
arrayOfVariantOfDouble116(5) = 0.000000
arrayOfVariantOfDouble116(6) = 0.000000
arrayOfVariantOfDouble116(7) = 0.000000
arrayOfVariantOfDouble116(8) = 1.000000
arrayOfVariantOfDouble116(9) = 1.166967
arrayOfVariantOfDouble116(10) = 0.000000
arrayOfVariantOfDouble116(11) = 0.000000
move2.Apply arrayOfVariantOfDouble116

Set move2 = product4.Move

Set move2 = move2.MovableObject

Dim arrayOfVariantOfDouble117(11)
arrayOfVariantOfDouble117(0) = 1.000000
arrayOfVariantOfDouble117(1) = 0.000000
arrayOfVariantOfDouble117(2) = 0.000000
arrayOfVariantOfDouble117(3) = 0.000000
arrayOfVariantOfDouble117(4) = 1.000000
arrayOfVariantOfDouble117(5) = 0.000000
arrayOfVariantOfDouble117(6) = 0.000000
arrayOfVariantOfDouble117(7) = 0.000000
arrayOfVariantOfDouble117(8) = 1.000000
arrayOfVariantOfDouble117(9) = 1.166978
arrayOfVariantOfDouble117(10) = 0.000000
arrayOfVariantOfDouble117(11) = 0.000000
move2.Apply arrayOfVariantOfDouble117

Set move2 = product4.Move

Set move2 = move2.MovableObject

Dim arrayOfVariantOfDouble118(11)
arrayOfVariantOfDouble118(0) = 1.000000
arrayOfVariantOfDouble118(1) = 0.000000
arrayOfVariantOfDouble118(2) = 0.000000
arrayOfVariantOfDouble118(3) = 0.000000
arrayOfVariantOfDouble118(4) = 1.000000
arrayOfVariantOfDouble118(5) = 0.000000
arrayOfVariantOfDouble118(6) = 0.000000
arrayOfVariantOfDouble118(7) = 0.000000
arrayOfVariantOfDouble118(8) = 1.000000
arrayOfVariantOfDouble118(9) = 0.583480
arrayOfVariantOfDouble118(10) = 0.000000
arrayOfVariantOfDouble118(11) = 0.000000
move2.Apply arrayOfVariantOfDouble118

Set move2 = product4.Move

Set move2 = move2.MovableObject

Dim arrayOfVariantOfDouble119(11)
arrayOfVariantOfDouble119(0) = 1.000000
arrayOfVariantOfDouble119(1) = 0.000000
arrayOfVariantOfDouble119(2) = 0.000000
arrayOfVariantOfDouble119(3) = 0.000000
arrayOfVariantOfDouble119(4) = 1.000000
arrayOfVariantOfDouble119(5) = 0.000000
arrayOfVariantOfDouble119(6) = 0.000000
arrayOfVariantOfDouble119(7) = 0.000000
arrayOfVariantOfDouble119(8) = 1.000000
arrayOfVariantOfDouble119(9) = 1.750455
arrayOfVariantOfDouble119(10) = 0.000000
arrayOfVariantOfDouble119(11) = 0.000000
move2.Apply arrayOfVariantOfDouble119

Set move2 = product4.Move

Set move2 = move2.MovableObject

Dim arrayOfVariantOfDouble120(11)
arrayOfVariantOfDouble120(0) = 1.000000
arrayOfVariantOfDouble120(1) = 0.000000
arrayOfVariantOfDouble120(2) = 0.000000
arrayOfVariantOfDouble120(3) = 0.000000
arrayOfVariantOfDouble120(4) = 1.000000
arrayOfVariantOfDouble120(5) = 0.000000
arrayOfVariantOfDouble120(6) = 0.000000
arrayOfVariantOfDouble120(7) = 0.000000
arrayOfVariantOfDouble120(8) = 1.000000
arrayOfVariantOfDouble120(9) = 0.678800
arrayOfVariantOfDouble120(10) = 0.000000
arrayOfVariantOfDouble120(11) = 0.000000
move2.Apply arrayOfVariantOfDouble120

Set move2 = product4.Move

Set move2 = move2.MovableObject

Dim arrayOfVariantOfDouble121(11)
arrayOfVariantOfDouble121(0) = 1.000000
arrayOfVariantOfDouble121(1) = 0.000000
arrayOfVariantOfDouble121(2) = 0.000000
arrayOfVariantOfDouble121(3) = 0.000000
arrayOfVariantOfDouble121(4) = 1.000000
arrayOfVariantOfDouble121(5) = 0.000000
arrayOfVariantOfDouble121(6) = 0.000000
arrayOfVariantOfDouble121(7) = 0.000000
arrayOfVariantOfDouble121(8) = 1.000000
arrayOfVariantOfDouble121(9) = 1.750458
arrayOfVariantOfDouble121(10) = 0.000000
arrayOfVariantOfDouble121(11) = 0.000000
move2.Apply arrayOfVariantOfDouble121

Set move2 = product4.Move

Set move2 = move2.MovableObject

Dim arrayOfVariantOfDouble122(11)
arrayOfVariantOfDouble122(0) = 1.000000
arrayOfVariantOfDouble122(1) = 0.000000
arrayOfVariantOfDouble122(2) = 0.000000
arrayOfVariantOfDouble122(3) = 0.000000
arrayOfVariantOfDouble122(4) = 1.000000
arrayOfVariantOfDouble122(5) = 0.000000
arrayOfVariantOfDouble122(6) = 0.000000
arrayOfVariantOfDouble122(7) = 0.000000
arrayOfVariantOfDouble122(8) = 1.000000
arrayOfVariantOfDouble122(9) = 1.166967
arrayOfVariantOfDouble122(10) = 0.000000
arrayOfVariantOfDouble122(11) = 0.000000
move2.Apply arrayOfVariantOfDouble122

Set move2 = product4.Move

Set move2 = move2.MovableObject

Dim arrayOfVariantOfDouble123(11)
arrayOfVariantOfDouble123(0) = 1.000000
arrayOfVariantOfDouble123(1) = 0.000000
arrayOfVariantOfDouble123(2) = 0.000000
arrayOfVariantOfDouble123(3) = 0.000000
arrayOfVariantOfDouble123(4) = 1.000000
arrayOfVariantOfDouble123(5) = 0.000000
arrayOfVariantOfDouble123(6) = 0.000000
arrayOfVariantOfDouble123(7) = 0.000000
arrayOfVariantOfDouble123(8) = 1.000000
arrayOfVariantOfDouble123(9) = 1.166969
arrayOfVariantOfDouble123(10) = 0.000000
arrayOfVariantOfDouble123(11) = 0.000000
move2.Apply arrayOfVariantOfDouble123

Set move2 = product4.Move

Set move2 = move2.MovableObject

Dim arrayOfVariantOfDouble124(11)
arrayOfVariantOfDouble124(0) = 1.000000
arrayOfVariantOfDouble124(1) = 0.000000
arrayOfVariantOfDouble124(2) = 0.000000
arrayOfVariantOfDouble124(3) = 0.000000
arrayOfVariantOfDouble124(4) = 1.000000
arrayOfVariantOfDouble124(5) = 0.000000
arrayOfVariantOfDouble124(6) = 0.000000
arrayOfVariantOfDouble124(7) = 0.000000
arrayOfVariantOfDouble124(8) = 1.000000
arrayOfVariantOfDouble124(9) = 1.262281
arrayOfVariantOfDouble124(10) = 0.000000
arrayOfVariantOfDouble124(11) = 0.000000
move2.Apply arrayOfVariantOfDouble124

Set move2 = product4.Move

Set move2 = move2.MovableObject

Dim arrayOfVariantOfDouble125(11)
arrayOfVariantOfDouble125(0) = 1.000000
arrayOfVariantOfDouble125(1) = 0.000000
arrayOfVariantOfDouble125(2) = 0.000000
arrayOfVariantOfDouble125(3) = 0.000000
arrayOfVariantOfDouble125(4) = 1.000000
arrayOfVariantOfDouble125(5) = 0.000000
arrayOfVariantOfDouble125(6) = 0.000000
arrayOfVariantOfDouble125(7) = 0.000000
arrayOfVariantOfDouble125(8) = 1.000000
arrayOfVariantOfDouble125(9) = 1.750455
arrayOfVariantOfDouble125(10) = 0.000000
arrayOfVariantOfDouble125(11) = 0.000000
move2.Apply arrayOfVariantOfDouble125

Set move2 = product4.Move

Set move2 = move2.MovableObject

Dim arrayOfVariantOfDouble126(11)
arrayOfVariantOfDouble126(0) = 1.000000
arrayOfVariantOfDouble126(1) = 0.000000
arrayOfVariantOfDouble126(2) = 0.000000
arrayOfVariantOfDouble126(3) = 0.000000
arrayOfVariantOfDouble126(4) = 1.000000
arrayOfVariantOfDouble126(5) = 0.000000
arrayOfVariantOfDouble126(6) = 0.000000
arrayOfVariantOfDouble126(7) = 0.000000
arrayOfVariantOfDouble126(8) = 1.000000
arrayOfVariantOfDouble126(9) = 0.583489
arrayOfVariantOfDouble126(10) = 0.000000
arrayOfVariantOfDouble126(11) = 0.000000
move2.Apply arrayOfVariantOfDouble126

Set move2 = product4.Move

Set move2 = move2.MovableObject

Dim arrayOfVariantOfDouble127(11)
arrayOfVariantOfDouble127(0) = 1.000000
arrayOfVariantOfDouble127(1) = 0.000000
arrayOfVariantOfDouble127(2) = 0.000000
arrayOfVariantOfDouble127(3) = 0.000000
arrayOfVariantOfDouble127(4) = 1.000000
arrayOfVariantOfDouble127(5) = 0.000000
arrayOfVariantOfDouble127(6) = 0.000000
arrayOfVariantOfDouble127(7) = 0.000000
arrayOfVariantOfDouble127(8) = 1.000000
arrayOfVariantOfDouble127(9) = 1.845770
arrayOfVariantOfDouble127(10) = 0.000000
arrayOfVariantOfDouble127(11) = 0.000000
move2.Apply arrayOfVariantOfDouble127

Set move2 = product4.Move

Set move2 = move2.MovableObject

Dim arrayOfVariantOfDouble128(11)
arrayOfVariantOfDouble128(0) = 1.000000
arrayOfVariantOfDouble128(1) = 0.000000
arrayOfVariantOfDouble128(2) = 0.000000
arrayOfVariantOfDouble128(3) = 0.000000
arrayOfVariantOfDouble128(4) = 1.000000
arrayOfVariantOfDouble128(5) = 0.000000
arrayOfVariantOfDouble128(6) = 0.000000
arrayOfVariantOfDouble128(7) = 0.000000
arrayOfVariantOfDouble128(8) = 1.000000
arrayOfVariantOfDouble128(9) = 0.583481
arrayOfVariantOfDouble128(10) = 0.000000
arrayOfVariantOfDouble128(11) = 0.000000
move2.Apply arrayOfVariantOfDouble128

Set move2 = product4.Move

Set move2 = move2.MovableObject

Dim arrayOfVariantOfDouble129(11)
arrayOfVariantOfDouble129(0) = 1.000000
arrayOfVariantOfDouble129(1) = 0.000000
arrayOfVariantOfDouble129(2) = 0.000000
arrayOfVariantOfDouble129(3) = 0.000000
arrayOfVariantOfDouble129(4) = 1.000000
arrayOfVariantOfDouble129(5) = 0.000000
arrayOfVariantOfDouble129(6) = 0.000000
arrayOfVariantOfDouble129(7) = 0.000000
arrayOfVariantOfDouble129(8) = 1.000000
arrayOfVariantOfDouble129(9) = 1.845766
arrayOfVariantOfDouble129(10) = 0.000000
arrayOfVariantOfDouble129(11) = 0.000000
move2.Apply arrayOfVariantOfDouble129

Set move2 = product4.Move

Set move2 = move2.MovableObject

Dim arrayOfVariantOfDouble130(11)
arrayOfVariantOfDouble130(0) = 1.000000
arrayOfVariantOfDouble130(1) = 0.000000
arrayOfVariantOfDouble130(2) = 0.000000
arrayOfVariantOfDouble130(3) = 0.000000
arrayOfVariantOfDouble130(4) = 1.000000
arrayOfVariantOfDouble130(5) = 0.000000
arrayOfVariantOfDouble130(6) = 0.000000
arrayOfVariantOfDouble130(7) = 0.000000
arrayOfVariantOfDouble130(8) = 1.000000
arrayOfVariantOfDouble130(9) = 1.166970
arrayOfVariantOfDouble130(10) = 0.000000
arrayOfVariantOfDouble130(11) = 0.000000
move2.Apply arrayOfVariantOfDouble130

Set move2 = product4.Move

Set move2 = move2.MovableObject

Dim arrayOfVariantOfDouble131(11)
arrayOfVariantOfDouble131(0) = 1.000000
arrayOfVariantOfDouble131(1) = 0.000000
arrayOfVariantOfDouble131(2) = 0.000000
arrayOfVariantOfDouble131(3) = 0.000000
arrayOfVariantOfDouble131(4) = 1.000000
arrayOfVariantOfDouble131(5) = 0.000000
arrayOfVariantOfDouble131(6) = 0.000000
arrayOfVariantOfDouble131(7) = 0.000000
arrayOfVariantOfDouble131(8) = 1.000000
arrayOfVariantOfDouble131(9) = 1.262284
arrayOfVariantOfDouble131(10) = 0.000000
arrayOfVariantOfDouble131(11) = 0.000000
move2.Apply arrayOfVariantOfDouble131

Set move2 = product4.Move

Set move2 = move2.MovableObject

Dim arrayOfVariantOfDouble132(11)
arrayOfVariantOfDouble132(0) = 1.000000
arrayOfVariantOfDouble132(1) = 0.000000
arrayOfVariantOfDouble132(2) = 0.000000
arrayOfVariantOfDouble132(3) = 0.000000
arrayOfVariantOfDouble132(4) = 1.000000
arrayOfVariantOfDouble132(5) = 0.000000
arrayOfVariantOfDouble132(6) = 0.000000
arrayOfVariantOfDouble132(7) = 0.000000
arrayOfVariantOfDouble132(8) = 1.000000
arrayOfVariantOfDouble132(9) = 1.166974
arrayOfVariantOfDouble132(10) = 0.000000
arrayOfVariantOfDouble132(11) = 0.000000
move2.Apply arrayOfVariantOfDouble132

Set move2 = product4.Move

Set move2 = move2.MovableObject

Dim arrayOfVariantOfDouble133(11)
arrayOfVariantOfDouble133(0) = 1.000000
arrayOfVariantOfDouble133(1) = 0.000000
arrayOfVariantOfDouble133(2) = 0.000000
arrayOfVariantOfDouble133(3) = 0.000000
arrayOfVariantOfDouble133(4) = 1.000000
arrayOfVariantOfDouble133(5) = 0.000000
arrayOfVariantOfDouble133(6) = 0.000000
arrayOfVariantOfDouble133(7) = 0.000000
arrayOfVariantOfDouble133(8) = 1.000000
arrayOfVariantOfDouble133(9) = 1.845765
arrayOfVariantOfDouble133(10) = 0.000000
arrayOfVariantOfDouble133(11) = 0.000000
move2.Apply arrayOfVariantOfDouble133

Set move2 = product4.Move

Set move2 = move2.MovableObject

Dim arrayOfVariantOfDouble134(11)
arrayOfVariantOfDouble134(0) = 1.000000
arrayOfVariantOfDouble134(1) = 0.000000
arrayOfVariantOfDouble134(2) = 0.000000
arrayOfVariantOfDouble134(3) = 0.000000
arrayOfVariantOfDouble134(4) = 1.000000
arrayOfVariantOfDouble134(5) = 0.000000
arrayOfVariantOfDouble134(6) = 0.000000
arrayOfVariantOfDouble134(7) = 0.000000
arrayOfVariantOfDouble134(8) = 1.000000
arrayOfVariantOfDouble134(9) = 1.750453
arrayOfVariantOfDouble134(10) = 0.000000
arrayOfVariantOfDouble134(11) = 0.000000
move2.Apply arrayOfVariantOfDouble134

Set move2 = product4.Move

Set move2 = move2.MovableObject

Dim arrayOfVariantOfDouble135(11)
arrayOfVariantOfDouble135(0) = 1.000000
arrayOfVariantOfDouble135(1) = 0.000000
arrayOfVariantOfDouble135(2) = 0.000000
arrayOfVariantOfDouble135(3) = 0.000000
arrayOfVariantOfDouble135(4) = 1.000000
arrayOfVariantOfDouble135(5) = 0.000000
arrayOfVariantOfDouble135(6) = 0.000000
arrayOfVariantOfDouble135(7) = 0.000000
arrayOfVariantOfDouble135(8) = 1.000000
arrayOfVariantOfDouble135(9) = 1.166969
arrayOfVariantOfDouble135(10) = 0.000000
arrayOfVariantOfDouble135(11) = 0.000000
move2.Apply arrayOfVariantOfDouble135

Set move2 = product4.Move

Set move2 = move2.MovableObject

Dim arrayOfVariantOfDouble136(11)
arrayOfVariantOfDouble136(0) = 1.000000
arrayOfVariantOfDouble136(1) = 0.000000
arrayOfVariantOfDouble136(2) = 0.000000
arrayOfVariantOfDouble136(3) = 0.000000
arrayOfVariantOfDouble136(4) = 1.000000
arrayOfVariantOfDouble136(5) = 0.000000
arrayOfVariantOfDouble136(6) = 0.000000
arrayOfVariantOfDouble136(7) = 0.000000
arrayOfVariantOfDouble136(8) = 1.000000
arrayOfVariantOfDouble136(9) = 1.262285
arrayOfVariantOfDouble136(10) = 0.000000
arrayOfVariantOfDouble136(11) = 0.000000
move2.Apply arrayOfVariantOfDouble136

Set move2 = product4.Move

Set move2 = move2.MovableObject

Dim arrayOfVariantOfDouble137(11)
arrayOfVariantOfDouble137(0) = 1.000000
arrayOfVariantOfDouble137(1) = 0.000000
arrayOfVariantOfDouble137(2) = 0.000000
arrayOfVariantOfDouble137(3) = 0.000000
arrayOfVariantOfDouble137(4) = 1.000000
arrayOfVariantOfDouble137(5) = 0.000000
arrayOfVariantOfDouble137(6) = 0.000000
arrayOfVariantOfDouble137(7) = 0.000000
arrayOfVariantOfDouble137(8) = 1.000000
arrayOfVariantOfDouble137(9) = 1.262283
arrayOfVariantOfDouble137(10) = 0.000000
arrayOfVariantOfDouble137(11) = 0.000000
move2.Apply arrayOfVariantOfDouble137

Set move2 = product4.Move

Set move2 = move2.MovableObject

Dim arrayOfVariantOfDouble138(11)
arrayOfVariantOfDouble138(0) = 1.000000
arrayOfVariantOfDouble138(1) = 0.000000
arrayOfVariantOfDouble138(2) = 0.000000
arrayOfVariantOfDouble138(3) = 0.000000
arrayOfVariantOfDouble138(4) = 1.000000
arrayOfVariantOfDouble138(5) = 0.000000
arrayOfVariantOfDouble138(6) = 0.000000
arrayOfVariantOfDouble138(7) = 0.000000
arrayOfVariantOfDouble138(8) = 1.000000
arrayOfVariantOfDouble138(9) = 1.166971
arrayOfVariantOfDouble138(10) = 0.000000
arrayOfVariantOfDouble138(11) = 0.000000
move2.Apply arrayOfVariantOfDouble138

Set move2 = product4.Move

Set move2 = move2.MovableObject

Dim arrayOfVariantOfDouble139(11)
arrayOfVariantOfDouble139(0) = 1.000000
arrayOfVariantOfDouble139(1) = 0.000000
arrayOfVariantOfDouble139(2) = 0.000000
arrayOfVariantOfDouble139(3) = 0.000000
arrayOfVariantOfDouble139(4) = 1.000000
arrayOfVariantOfDouble139(5) = 0.000000
arrayOfVariantOfDouble139(6) = 0.000000
arrayOfVariantOfDouble139(7) = 0.000000
arrayOfVariantOfDouble139(8) = 1.000000
arrayOfVariantOfDouble139(9) = 1.166971
arrayOfVariantOfDouble139(10) = 0.000000
arrayOfVariantOfDouble139(11) = 0.000000
move2.Apply arrayOfVariantOfDouble139

Set move2 = product4.Move

Set move2 = move2.MovableObject

Dim arrayOfVariantOfDouble140(11)
arrayOfVariantOfDouble140(0) = 1.000000
arrayOfVariantOfDouble140(1) = 0.000000
arrayOfVariantOfDouble140(2) = 0.000000
arrayOfVariantOfDouble140(3) = 0.000000
arrayOfVariantOfDouble140(4) = 1.000000
arrayOfVariantOfDouble140(5) = 0.000000
arrayOfVariantOfDouble140(6) = 0.000000
arrayOfVariantOfDouble140(7) = 0.000000
arrayOfVariantOfDouble140(8) = 1.000000
arrayOfVariantOfDouble140(9) = 1.845767
arrayOfVariantOfDouble140(10) = 0.000000
arrayOfVariantOfDouble140(11) = 0.000000
move2.Apply arrayOfVariantOfDouble140

Set move2 = product4.Move

Set move2 = move2.MovableObject

Dim arrayOfVariantOfDouble141(11)
arrayOfVariantOfDouble141(0) = 1.000000
arrayOfVariantOfDouble141(1) = 0.000000
arrayOfVariantOfDouble141(2) = 0.000000
arrayOfVariantOfDouble141(3) = 0.000000
arrayOfVariantOfDouble141(4) = 1.000000
arrayOfVariantOfDouble141(5) = 0.000000
arrayOfVariantOfDouble141(6) = 0.000000
arrayOfVariantOfDouble141(7) = 0.000000
arrayOfVariantOfDouble141(8) = 1.000000
arrayOfVariantOfDouble141(9) = 1.166976
arrayOfVariantOfDouble141(10) = 0.000000
arrayOfVariantOfDouble141(11) = 0.000000
move2.Apply arrayOfVariantOfDouble141

Set move2 = product4.Move

Set move2 = move2.MovableObject

Dim arrayOfVariantOfDouble142(11)
arrayOfVariantOfDouble142(0) = 1.000000
arrayOfVariantOfDouble142(1) = 0.000000
arrayOfVariantOfDouble142(2) = 0.000000
arrayOfVariantOfDouble142(3) = 0.000000
arrayOfVariantOfDouble142(4) = 1.000000
arrayOfVariantOfDouble142(5) = 0.000000
arrayOfVariantOfDouble142(6) = 0.000000
arrayOfVariantOfDouble142(7) = 0.000000
arrayOfVariantOfDouble142(8) = 1.000000
arrayOfVariantOfDouble142(9) = 1.166964
arrayOfVariantOfDouble142(10) = 0.000000
arrayOfVariantOfDouble142(11) = 0.000000
move2.Apply arrayOfVariantOfDouble142

Set move2 = product4.Move

Set move2 = move2.MovableObject

Dim arrayOfVariantOfDouble143(11)
arrayOfVariantOfDouble143(0) = 1.000000
arrayOfVariantOfDouble143(1) = 0.000000
arrayOfVariantOfDouble143(2) = 0.000000
arrayOfVariantOfDouble143(3) = 0.000000
arrayOfVariantOfDouble143(4) = 1.000000
arrayOfVariantOfDouble143(5) = 0.000000
arrayOfVariantOfDouble143(6) = 0.000000
arrayOfVariantOfDouble143(7) = 0.000000
arrayOfVariantOfDouble143(8) = 1.000000
arrayOfVariantOfDouble143(9) = 0.678802
arrayOfVariantOfDouble143(10) = 0.000000
arrayOfVariantOfDouble143(11) = 0.000000
move2.Apply arrayOfVariantOfDouble143

Set move2 = product4.Move

Set move2 = move2.MovableObject

Dim arrayOfVariantOfDouble144(11)
arrayOfVariantOfDouble144(0) = 1.000000
arrayOfVariantOfDouble144(1) = 0.000000
arrayOfVariantOfDouble144(2) = 0.000000
arrayOfVariantOfDouble144(3) = 0.000000
arrayOfVariantOfDouble144(4) = 1.000000
arrayOfVariantOfDouble144(5) = 0.000000
arrayOfVariantOfDouble144(6) = 0.000000
arrayOfVariantOfDouble144(7) = 0.000000
arrayOfVariantOfDouble144(8) = 1.000000
arrayOfVariantOfDouble144(9) = 1.166971
arrayOfVariantOfDouble144(10) = 0.000000
arrayOfVariantOfDouble144(11) = 0.000000
move2.Apply arrayOfVariantOfDouble144

Set move2 = product4.Move

Set move2 = move2.MovableObject

Dim arrayOfVariantOfDouble145(11)
arrayOfVariantOfDouble145(0) = 1.000000
arrayOfVariantOfDouble145(1) = 0.000000
arrayOfVariantOfDouble145(2) = 0.000000
arrayOfVariantOfDouble145(3) = 0.000000
arrayOfVariantOfDouble145(4) = 1.000000
arrayOfVariantOfDouble145(5) = 0.000000
arrayOfVariantOfDouble145(6) = 0.000000
arrayOfVariantOfDouble145(7) = 0.000000
arrayOfVariantOfDouble145(8) = 1.000000
arrayOfVariantOfDouble145(9) = 1.166969
arrayOfVariantOfDouble145(10) = 0.000000
arrayOfVariantOfDouble145(11) = 0.000000
move2.Apply arrayOfVariantOfDouble145

Set move2 = product4.Move

Set move2 = move2.MovableObject

Dim arrayOfVariantOfDouble146(11)
arrayOfVariantOfDouble146(0) = 1.000000
arrayOfVariantOfDouble146(1) = 0.000000
arrayOfVariantOfDouble146(2) = 0.000000
arrayOfVariantOfDouble146(3) = 0.000000
arrayOfVariantOfDouble146(4) = 1.000000
arrayOfVariantOfDouble146(5) = 0.000000
arrayOfVariantOfDouble146(6) = 0.000000
arrayOfVariantOfDouble146(7) = 0.000000
arrayOfVariantOfDouble146(8) = 1.000000
arrayOfVariantOfDouble146(9) = 1.750453
arrayOfVariantOfDouble146(10) = 0.000000
arrayOfVariantOfDouble146(11) = 0.000000
move2.Apply arrayOfVariantOfDouble146

Set move2 = product4.Move

Set move2 = move2.MovableObject

Dim arrayOfVariantOfDouble147(11)
arrayOfVariantOfDouble147(0) = 1.000000
arrayOfVariantOfDouble147(1) = 0.000000
arrayOfVariantOfDouble147(2) = 0.000000
arrayOfVariantOfDouble147(3) = 0.000000
arrayOfVariantOfDouble147(4) = 1.000000
arrayOfVariantOfDouble147(5) = 0.000000
arrayOfVariantOfDouble147(6) = 0.000000
arrayOfVariantOfDouble147(7) = 0.000000
arrayOfVariantOfDouble147(8) = 1.000000
arrayOfVariantOfDouble147(9) = 1.262283
arrayOfVariantOfDouble147(10) = 0.000000
arrayOfVariantOfDouble147(11) = 0.000000
move2.Apply arrayOfVariantOfDouble147

Set move2 = product4.Move

Set move2 = move2.MovableObject

Dim arrayOfVariantOfDouble148(11)
arrayOfVariantOfDouble148(0) = 1.000000
arrayOfVariantOfDouble148(1) = 0.000000
arrayOfVariantOfDouble148(2) = 0.000000
arrayOfVariantOfDouble148(3) = 0.000000
arrayOfVariantOfDouble148(4) = 1.000000
arrayOfVariantOfDouble148(5) = 0.000000
arrayOfVariantOfDouble148(6) = 0.000000
arrayOfVariantOfDouble148(7) = 0.000000
arrayOfVariantOfDouble148(8) = 1.000000
arrayOfVariantOfDouble148(9) = 1.166971
arrayOfVariantOfDouble148(10) = 0.000000
arrayOfVariantOfDouble148(11) = 0.000000
move2.Apply arrayOfVariantOfDouble148

Set move2 = product4.Move

Set move2 = move2.MovableObject

Dim arrayOfVariantOfDouble149(11)
arrayOfVariantOfDouble149(0) = 1.000000
arrayOfVariantOfDouble149(1) = 0.000000
arrayOfVariantOfDouble149(2) = 0.000000
arrayOfVariantOfDouble149(3) = 0.000000
arrayOfVariantOfDouble149(4) = 1.000000
arrayOfVariantOfDouble149(5) = 0.000000
arrayOfVariantOfDouble149(6) = 0.000000
arrayOfVariantOfDouble149(7) = 0.000000
arrayOfVariantOfDouble149(8) = 1.000000
arrayOfVariantOfDouble149(9) = 1.845773
arrayOfVariantOfDouble149(10) = 0.000000
arrayOfVariantOfDouble149(11) = 0.000000
move2.Apply arrayOfVariantOfDouble149

Set move2 = product4.Move

Set move2 = move2.MovableObject

Dim arrayOfVariantOfDouble150(11)
arrayOfVariantOfDouble150(0) = 1.000000
arrayOfVariantOfDouble150(1) = 0.000000
arrayOfVariantOfDouble150(2) = 0.000000
arrayOfVariantOfDouble150(3) = 0.000000
arrayOfVariantOfDouble150(4) = 1.000000
arrayOfVariantOfDouble150(5) = 0.000000
arrayOfVariantOfDouble150(6) = 0.000000
arrayOfVariantOfDouble150(7) = 0.000000
arrayOfVariantOfDouble150(8) = 1.000000
arrayOfVariantOfDouble150(9) = 1.750451
arrayOfVariantOfDouble150(10) = 0.000000
arrayOfVariantOfDouble150(11) = 0.000000
move2.Apply arrayOfVariantOfDouble150

Set move2 = product4.Move

Set move2 = move2.MovableObject

Dim arrayOfVariantOfDouble151(11)
arrayOfVariantOfDouble151(0) = 1.000000
arrayOfVariantOfDouble151(1) = 0.000000
arrayOfVariantOfDouble151(2) = 0.000000
arrayOfVariantOfDouble151(3) = 0.000000
arrayOfVariantOfDouble151(4) = 1.000000
arrayOfVariantOfDouble151(5) = 0.000000
arrayOfVariantOfDouble151(6) = 0.000000
arrayOfVariantOfDouble151(7) = 0.000000
arrayOfVariantOfDouble151(8) = 1.000000
arrayOfVariantOfDouble151(9) = 0.583489
arrayOfVariantOfDouble151(10) = 0.000000
arrayOfVariantOfDouble151(11) = 0.000000
move2.Apply arrayOfVariantOfDouble151

Set move2 = product4.Move

Set move2 = move2.MovableObject

Dim arrayOfVariantOfDouble152(11)
arrayOfVariantOfDouble152(0) = 1.000000
arrayOfVariantOfDouble152(1) = 0.000000
arrayOfVariantOfDouble152(2) = 0.000000
arrayOfVariantOfDouble152(3) = 0.000000
arrayOfVariantOfDouble152(4) = 1.000000
arrayOfVariantOfDouble152(5) = 0.000000
arrayOfVariantOfDouble152(6) = 0.000000
arrayOfVariantOfDouble152(7) = 0.000000
arrayOfVariantOfDouble152(8) = 1.000000
arrayOfVariantOfDouble152(9) = 1.845766
arrayOfVariantOfDouble152(10) = 0.000000
arrayOfVariantOfDouble152(11) = 0.000000
move2.Apply arrayOfVariantOfDouble152

Set move2 = product4.Move

Set move2 = move2.MovableObject

Dim arrayOfVariantOfDouble153(11)
arrayOfVariantOfDouble153(0) = 1.000000
arrayOfVariantOfDouble153(1) = 0.000000
arrayOfVariantOfDouble153(2) = 0.000000
arrayOfVariantOfDouble153(3) = 0.000000
arrayOfVariantOfDouble153(4) = 1.000000
arrayOfVariantOfDouble153(5) = 0.000000
arrayOfVariantOfDouble153(6) = 0.000000
arrayOfVariantOfDouble153(7) = 0.000000
arrayOfVariantOfDouble153(8) = 1.000000
arrayOfVariantOfDouble153(9) = 1.166972
arrayOfVariantOfDouble153(10) = 0.000000
arrayOfVariantOfDouble153(11) = 0.000000
move2.Apply arrayOfVariantOfDouble153

Set move2 = product4.Move

Set move2 = move2.MovableObject

Dim arrayOfVariantOfDouble154(11)
arrayOfVariantOfDouble154(0) = 1.000000
arrayOfVariantOfDouble154(1) = 0.000000
arrayOfVariantOfDouble154(2) = 0.000000
arrayOfVariantOfDouble154(3) = 0.000000
arrayOfVariantOfDouble154(4) = 1.000000
arrayOfVariantOfDouble154(5) = 0.000000
arrayOfVariantOfDouble154(6) = 0.000000
arrayOfVariantOfDouble154(7) = 0.000000
arrayOfVariantOfDouble154(8) = 1.000000
arrayOfVariantOfDouble154(9) = 1.750451
arrayOfVariantOfDouble154(10) = 0.000000
arrayOfVariantOfDouble154(11) = 0.000000
move2.Apply arrayOfVariantOfDouble154

Set move2 = product4.Move

Set move2 = move2.MovableObject

Dim arrayOfVariantOfDouble155(11)
arrayOfVariantOfDouble155(0) = 1.000000
arrayOfVariantOfDouble155(1) = 0.000000
arrayOfVariantOfDouble155(2) = 0.000000
arrayOfVariantOfDouble155(3) = 0.000000
arrayOfVariantOfDouble155(4) = 1.000000
arrayOfVariantOfDouble155(5) = 0.000000
arrayOfVariantOfDouble155(6) = 0.000000
arrayOfVariantOfDouble155(7) = 0.000000
arrayOfVariantOfDouble155(8) = 1.000000
arrayOfVariantOfDouble155(9) = 2.429255
arrayOfVariantOfDouble155(10) = 0.000000
arrayOfVariantOfDouble155(11) = 0.000000
move2.Apply arrayOfVariantOfDouble155

Set move2 = product4.Move

Set move2 = move2.MovableObject

Dim arrayOfVariantOfDouble156(11)
arrayOfVariantOfDouble156(0) = 1.000000
arrayOfVariantOfDouble156(1) = 0.000000
arrayOfVariantOfDouble156(2) = 0.000000
arrayOfVariantOfDouble156(3) = 0.000000
arrayOfVariantOfDouble156(4) = 1.000000
arrayOfVariantOfDouble156(5) = 0.000000
arrayOfVariantOfDouble156(6) = 0.000000
arrayOfVariantOfDouble156(7) = 0.000000
arrayOfVariantOfDouble156(8) = 1.000000
arrayOfVariantOfDouble156(9) = 1.166970
arrayOfVariantOfDouble156(10) = 0.000000
arrayOfVariantOfDouble156(11) = 0.000000
move2.Apply arrayOfVariantOfDouble156

Set move2 = product4.Move

Set move2 = move2.MovableObject

Dim arrayOfVariantOfDouble157(11)
arrayOfVariantOfDouble157(0) = 1.000000
arrayOfVariantOfDouble157(1) = 0.000000
arrayOfVariantOfDouble157(2) = 0.000000
arrayOfVariantOfDouble157(3) = 0.000000
arrayOfVariantOfDouble157(4) = 1.000000
arrayOfVariantOfDouble157(5) = 0.000000
arrayOfVariantOfDouble157(6) = 0.000000
arrayOfVariantOfDouble157(7) = 0.000000
arrayOfVariantOfDouble157(8) = 1.000000
arrayOfVariantOfDouble157(9) = 2.429254
arrayOfVariantOfDouble157(10) = 0.000000
arrayOfVariantOfDouble157(11) = 0.000000
move2.Apply arrayOfVariantOfDouble157

Set move2 = product4.Move

Set move2 = move2.MovableObject

Dim arrayOfVariantOfDouble158(11)
arrayOfVariantOfDouble158(0) = 1.000000
arrayOfVariantOfDouble158(1) = 0.000000
arrayOfVariantOfDouble158(2) = 0.000000
arrayOfVariantOfDouble158(3) = 0.000000
arrayOfVariantOfDouble158(4) = 1.000000
arrayOfVariantOfDouble158(5) = 0.000000
arrayOfVariantOfDouble158(6) = 0.000000
arrayOfVariantOfDouble158(7) = 0.000000
arrayOfVariantOfDouble158(8) = 1.000000
arrayOfVariantOfDouble158(9) = 1.166971
arrayOfVariantOfDouble158(10) = 0.000000
arrayOfVariantOfDouble158(11) = 0.000000
move2.Apply arrayOfVariantOfDouble158

Set move2 = product4.Move

Set move2 = move2.MovableObject

Dim arrayOfVariantOfDouble159(11)
arrayOfVariantOfDouble159(0) = 1.000000
arrayOfVariantOfDouble159(1) = 0.000000
arrayOfVariantOfDouble159(2) = 0.000000
arrayOfVariantOfDouble159(3) = 0.000000
arrayOfVariantOfDouble159(4) = 1.000000
arrayOfVariantOfDouble159(5) = 0.000000
arrayOfVariantOfDouble159(6) = 0.000000
arrayOfVariantOfDouble159(7) = 0.000000
arrayOfVariantOfDouble159(8) = 1.000000
arrayOfVariantOfDouble159(9) = 1.845767
arrayOfVariantOfDouble159(10) = 0.000000
arrayOfVariantOfDouble159(11) = 0.000000
move2.Apply arrayOfVariantOfDouble159

Set move2 = product4.Move

Set move2 = move2.MovableObject

Dim arrayOfVariantOfDouble160(11)
arrayOfVariantOfDouble160(0) = 1.000000
arrayOfVariantOfDouble160(1) = 0.000000
arrayOfVariantOfDouble160(2) = 0.000000
arrayOfVariantOfDouble160(3) = 0.000000
arrayOfVariantOfDouble160(4) = 1.000000
arrayOfVariantOfDouble160(5) = 0.000000
arrayOfVariantOfDouble160(6) = 0.000000
arrayOfVariantOfDouble160(7) = 0.000000
arrayOfVariantOfDouble160(8) = 1.000000
arrayOfVariantOfDouble160(9) = 2.917427
arrayOfVariantOfDouble160(10) = 0.000000
arrayOfVariantOfDouble160(11) = 0.000000
move2.Apply arrayOfVariantOfDouble160

Set move2 = product4.Move

Set move2 = move2.MovableObject

Dim arrayOfVariantOfDouble161(11)
arrayOfVariantOfDouble161(0) = 1.000000
arrayOfVariantOfDouble161(1) = 0.000000
arrayOfVariantOfDouble161(2) = 0.000000
arrayOfVariantOfDouble161(3) = 0.000000
arrayOfVariantOfDouble161(4) = 1.000000
arrayOfVariantOfDouble161(5) = 0.000000
arrayOfVariantOfDouble161(6) = 0.000000
arrayOfVariantOfDouble161(7) = 0.000000
arrayOfVariantOfDouble161(8) = 1.000000
arrayOfVariantOfDouble161(9) = 1.845767
arrayOfVariantOfDouble161(10) = 0.000000
arrayOfVariantOfDouble161(11) = 0.000000
move2.Apply arrayOfVariantOfDouble161

Set move2 = product4.Move

Set move2 = move2.MovableObject

Dim arrayOfVariantOfDouble162(11)
arrayOfVariantOfDouble162(0) = 1.000000
arrayOfVariantOfDouble162(1) = 0.000000
arrayOfVariantOfDouble162(2) = 0.000000
arrayOfVariantOfDouble162(3) = 0.000000
arrayOfVariantOfDouble162(4) = 1.000000
arrayOfVariantOfDouble162(5) = 0.000000
arrayOfVariantOfDouble162(6) = 0.000000
arrayOfVariantOfDouble162(7) = 0.000000
arrayOfVariantOfDouble162(8) = 1.000000
arrayOfVariantOfDouble162(9) = 2.333941
arrayOfVariantOfDouble162(10) = 0.000000
arrayOfVariantOfDouble162(11) = 0.000000
move2.Apply arrayOfVariantOfDouble162

Set move2 = product4.Move

Set move2 = move2.MovableObject

Dim arrayOfVariantOfDouble163(11)
arrayOfVariantOfDouble163(0) = 1.000000
arrayOfVariantOfDouble163(1) = 0.000000
arrayOfVariantOfDouble163(2) = 0.000000
arrayOfVariantOfDouble163(3) = 0.000000
arrayOfVariantOfDouble163(4) = 1.000000
arrayOfVariantOfDouble163(5) = 0.000000
arrayOfVariantOfDouble163(6) = 0.000000
arrayOfVariantOfDouble163(7) = 0.000000
arrayOfVariantOfDouble163(8) = 1.000000
arrayOfVariantOfDouble163(9) = 2.429254
arrayOfVariantOfDouble163(10) = 0.000000
arrayOfVariantOfDouble163(11) = 0.000000
move2.Apply arrayOfVariantOfDouble163

Set move2 = product4.Move

Set move2 = move2.MovableObject

Dim arrayOfVariantOfDouble164(11)
arrayOfVariantOfDouble164(0) = 1.000000
arrayOfVariantOfDouble164(1) = 0.000000
arrayOfVariantOfDouble164(2) = 0.000000
arrayOfVariantOfDouble164(3) = 0.000000
arrayOfVariantOfDouble164(4) = 1.000000
arrayOfVariantOfDouble164(5) = 0.000000
arrayOfVariantOfDouble164(6) = 0.000000
arrayOfVariantOfDouble164(7) = 0.000000
arrayOfVariantOfDouble164(8) = 1.000000
arrayOfVariantOfDouble164(9) = 3.012738
arrayOfVariantOfDouble164(10) = 0.000000
arrayOfVariantOfDouble164(11) = 0.000000
move2.Apply arrayOfVariantOfDouble164

Set move2 = product4.Move

Set move2 = move2.MovableObject

Dim arrayOfVariantOfDouble165(11)
arrayOfVariantOfDouble165(0) = 1.000000
arrayOfVariantOfDouble165(1) = 0.000000
arrayOfVariantOfDouble165(2) = 0.000000
arrayOfVariantOfDouble165(3) = 0.000000
arrayOfVariantOfDouble165(4) = 1.000000
arrayOfVariantOfDouble165(5) = 0.000000
arrayOfVariantOfDouble165(6) = 0.000000
arrayOfVariantOfDouble165(7) = 0.000000
arrayOfVariantOfDouble165(8) = 1.000000
arrayOfVariantOfDouble165(9) = 1.845771
arrayOfVariantOfDouble165(10) = 0.000000
arrayOfVariantOfDouble165(11) = 0.000000
move2.Apply arrayOfVariantOfDouble165

Set move2 = product4.Move

Set move2 = move2.MovableObject

Dim arrayOfVariantOfDouble166(11)
arrayOfVariantOfDouble166(0) = 1.000000
arrayOfVariantOfDouble166(1) = 0.000000
arrayOfVariantOfDouble166(2) = 0.000000
arrayOfVariantOfDouble166(3) = 0.000000
arrayOfVariantOfDouble166(4) = 1.000000
arrayOfVariantOfDouble166(5) = 0.000000
arrayOfVariantOfDouble166(6) = 0.000000
arrayOfVariantOfDouble166(7) = 0.000000
arrayOfVariantOfDouble166(8) = 1.000000
arrayOfVariantOfDouble166(9) = 3.596219
arrayOfVariantOfDouble166(10) = 0.000000
arrayOfVariantOfDouble166(11) = 0.000000
move2.Apply arrayOfVariantOfDouble166

Set move2 = product4.Move

Set move2 = move2.MovableObject

Dim arrayOfVariantOfDouble167(11)
arrayOfVariantOfDouble167(0) = 1.000000
arrayOfVariantOfDouble167(1) = 0.000000
arrayOfVariantOfDouble167(2) = 0.000000
arrayOfVariantOfDouble167(3) = 0.000000
arrayOfVariantOfDouble167(4) = 1.000000
arrayOfVariantOfDouble167(5) = 0.000000
arrayOfVariantOfDouble167(6) = 0.000000
arrayOfVariantOfDouble167(7) = 0.000000
arrayOfVariantOfDouble167(8) = 1.000000
arrayOfVariantOfDouble167(9) = 1.845772
arrayOfVariantOfDouble167(10) = 0.000000
arrayOfVariantOfDouble167(11) = 0.000000
move2.Apply arrayOfVariantOfDouble167

Set move2 = product4.Move

Set move2 = move2.MovableObject

Dim arrayOfVariantOfDouble168(11)
arrayOfVariantOfDouble168(0) = 1.000000
arrayOfVariantOfDouble168(1) = 0.000000
arrayOfVariantOfDouble168(2) = 0.000000
arrayOfVariantOfDouble168(3) = 0.000000
arrayOfVariantOfDouble168(4) = 1.000000
arrayOfVariantOfDouble168(5) = 0.000000
arrayOfVariantOfDouble168(6) = 0.000000
arrayOfVariantOfDouble168(7) = 0.000000
arrayOfVariantOfDouble168(8) = 1.000000
arrayOfVariantOfDouble168(9) = 2.429250
arrayOfVariantOfDouble168(10) = 0.000000
arrayOfVariantOfDouble168(11) = 0.000000
move2.Apply arrayOfVariantOfDouble168

Set move2 = product4.Move

Set move2 = move2.MovableObject

Dim arrayOfVariantOfDouble169(11)
arrayOfVariantOfDouble169(0) = 1.000000
arrayOfVariantOfDouble169(1) = 0.000000
arrayOfVariantOfDouble169(2) = 0.000000
arrayOfVariantOfDouble169(3) = 0.000000
arrayOfVariantOfDouble169(4) = 1.000000
arrayOfVariantOfDouble169(5) = 0.000000
arrayOfVariantOfDouble169(6) = 0.000000
arrayOfVariantOfDouble169(7) = 0.000000
arrayOfVariantOfDouble169(8) = 1.000000
arrayOfVariantOfDouble169(9) = 3.012742
arrayOfVariantOfDouble169(10) = 0.000000
arrayOfVariantOfDouble169(11) = 0.000000
move2.Apply arrayOfVariantOfDouble169

Set move2 = product4.Move

Set move2 = move2.MovableObject

Dim arrayOfVariantOfDouble170(11)
arrayOfVariantOfDouble170(0) = 1.000000
arrayOfVariantOfDouble170(1) = 0.000000
arrayOfVariantOfDouble170(2) = 0.000000
arrayOfVariantOfDouble170(3) = 0.000000
arrayOfVariantOfDouble170(4) = 1.000000
arrayOfVariantOfDouble170(5) = 0.000000
arrayOfVariantOfDouble170(6) = 0.000000
arrayOfVariantOfDouble170(7) = 0.000000
arrayOfVariantOfDouble170(8) = 1.000000
arrayOfVariantOfDouble170(9) = 2.429249
arrayOfVariantOfDouble170(10) = 0.000000
arrayOfVariantOfDouble170(11) = 0.000000
move2.Apply arrayOfVariantOfDouble170

Set move2 = product4.Move

Set move2 = move2.MovableObject

Dim arrayOfVariantOfDouble171(11)
arrayOfVariantOfDouble171(0) = 1.000000
arrayOfVariantOfDouble171(1) = 0.000000
arrayOfVariantOfDouble171(2) = 0.000000
arrayOfVariantOfDouble171(3) = 0.000000
arrayOfVariantOfDouble171(4) = 1.000000
arrayOfVariantOfDouble171(5) = 0.000000
arrayOfVariantOfDouble171(6) = 0.000000
arrayOfVariantOfDouble171(7) = 0.000000
arrayOfVariantOfDouble171(8) = 1.000000
arrayOfVariantOfDouble171(9) = 3.596231
arrayOfVariantOfDouble171(10) = 0.000000
arrayOfVariantOfDouble171(11) = 0.000000
move2.Apply arrayOfVariantOfDouble171

Set move2 = product4.Move

Set move2 = move2.MovableObject

Dim arrayOfVariantOfDouble172(11)
arrayOfVariantOfDouble172(0) = 1.000000
arrayOfVariantOfDouble172(1) = 0.000000
arrayOfVariantOfDouble172(2) = 0.000000
arrayOfVariantOfDouble172(3) = 0.000000
arrayOfVariantOfDouble172(4) = 1.000000
arrayOfVariantOfDouble172(5) = 0.000000
arrayOfVariantOfDouble172(6) = 0.000000
arrayOfVariantOfDouble172(7) = 0.000000
arrayOfVariantOfDouble172(8) = 1.000000
arrayOfVariantOfDouble172(9) = 2.429254
arrayOfVariantOfDouble172(10) = 0.000000
arrayOfVariantOfDouble172(11) = 0.000000
move2.Apply arrayOfVariantOfDouble172

Set move2 = product4.Move

Set move2 = move2.MovableObject

Dim arrayOfVariantOfDouble173(11)
arrayOfVariantOfDouble173(0) = 1.000000
arrayOfVariantOfDouble173(1) = 0.000000
arrayOfVariantOfDouble173(2) = 0.000000
arrayOfVariantOfDouble173(3) = 0.000000
arrayOfVariantOfDouble173(4) = 1.000000
arrayOfVariantOfDouble173(5) = 0.000000
arrayOfVariantOfDouble173(6) = 0.000000
arrayOfVariantOfDouble173(7) = 0.000000
arrayOfVariantOfDouble173(8) = 1.000000
arrayOfVariantOfDouble173(9) = 3.012732
arrayOfVariantOfDouble173(10) = 0.000000
arrayOfVariantOfDouble173(11) = 0.000000
move2.Apply arrayOfVariantOfDouble173

Set move2 = product4.Move

Set move2 = move2.MovableObject

Dim arrayOfVariantOfDouble174(11)
arrayOfVariantOfDouble174(0) = 1.000000
arrayOfVariantOfDouble174(1) = 0.000000
arrayOfVariantOfDouble174(2) = 0.000000
arrayOfVariantOfDouble174(3) = 0.000000
arrayOfVariantOfDouble174(4) = 1.000000
arrayOfVariantOfDouble174(5) = 0.000000
arrayOfVariantOfDouble174(6) = 0.000000
arrayOfVariantOfDouble174(7) = 0.000000
arrayOfVariantOfDouble174(8) = 1.000000
arrayOfVariantOfDouble174(9) = 3.012742
arrayOfVariantOfDouble174(10) = 0.000000
arrayOfVariantOfDouble174(11) = 0.000000
move2.Apply arrayOfVariantOfDouble174

Set move2 = product4.Move

Set move2 = move2.MovableObject

Dim arrayOfVariantOfDouble175(11)
arrayOfVariantOfDouble175(0) = 1.000000
arrayOfVariantOfDouble175(1) = 0.000000
arrayOfVariantOfDouble175(2) = 0.000000
arrayOfVariantOfDouble175(3) = 0.000000
arrayOfVariantOfDouble175(4) = 1.000000
arrayOfVariantOfDouble175(5) = 0.000000
arrayOfVariantOfDouble175(6) = 0.000000
arrayOfVariantOfDouble175(7) = 0.000000
arrayOfVariantOfDouble175(8) = 1.000000
arrayOfVariantOfDouble175(9) = 3.012741
arrayOfVariantOfDouble175(10) = 0.000000
arrayOfVariantOfDouble175(11) = 0.000000
move2.Apply arrayOfVariantOfDouble175

Set move2 = product4.Move

Set move2 = move2.MovableObject

Dim arrayOfVariantOfDouble176(11)
arrayOfVariantOfDouble176(0) = 1.000000
arrayOfVariantOfDouble176(1) = 0.000000
arrayOfVariantOfDouble176(2) = 0.000000
arrayOfVariantOfDouble176(3) = 0.000000
arrayOfVariantOfDouble176(4) = 1.000000
arrayOfVariantOfDouble176(5) = 0.000000
arrayOfVariantOfDouble176(6) = 0.000000
arrayOfVariantOfDouble176(7) = 0.000000
arrayOfVariantOfDouble176(8) = 1.000000
arrayOfVariantOfDouble176(9) = 3.012730
arrayOfVariantOfDouble176(10) = 0.000000
arrayOfVariantOfDouble176(11) = 0.000000
move2.Apply arrayOfVariantOfDouble176

Set move2 = product4.Move

Set move2 = move2.MovableObject

Dim arrayOfVariantOfDouble177(11)
arrayOfVariantOfDouble177(0) = 1.000000
arrayOfVariantOfDouble177(1) = 0.000000
arrayOfVariantOfDouble177(2) = 0.000000
arrayOfVariantOfDouble177(3) = 0.000000
arrayOfVariantOfDouble177(4) = 1.000000
arrayOfVariantOfDouble177(5) = 0.000000
arrayOfVariantOfDouble177(6) = 0.000000
arrayOfVariantOfDouble177(7) = 0.000000
arrayOfVariantOfDouble177(8) = 1.000000
arrayOfVariantOfDouble177(9) = 4.179709
arrayOfVariantOfDouble177(10) = 0.000000
arrayOfVariantOfDouble177(11) = 0.000000
move2.Apply arrayOfVariantOfDouble177

Set move2 = product4.Move

Set move2 = move2.MovableObject

Dim arrayOfVariantOfDouble178(11)
arrayOfVariantOfDouble178(0) = 1.000000
arrayOfVariantOfDouble178(1) = 0.000000
arrayOfVariantOfDouble178(2) = 0.000000
arrayOfVariantOfDouble178(3) = 0.000000
arrayOfVariantOfDouble178(4) = 1.000000
arrayOfVariantOfDouble178(5) = 0.000000
arrayOfVariantOfDouble178(6) = 0.000000
arrayOfVariantOfDouble178(7) = 0.000000
arrayOfVariantOfDouble178(8) = 1.000000
arrayOfVariantOfDouble178(9) = 3.012742
arrayOfVariantOfDouble178(10) = 0.000000
arrayOfVariantOfDouble178(11) = 0.000000
move2.Apply arrayOfVariantOfDouble178

Set move2 = product4.Move

Set move2 = move2.MovableObject

Dim arrayOfVariantOfDouble179(11)
arrayOfVariantOfDouble179(0) = 1.000000
arrayOfVariantOfDouble179(1) = 0.000000
arrayOfVariantOfDouble179(2) = 0.000000
arrayOfVariantOfDouble179(3) = 0.000000
arrayOfVariantOfDouble179(4) = 1.000000
arrayOfVariantOfDouble179(5) = 0.000000
arrayOfVariantOfDouble179(6) = 0.000000
arrayOfVariantOfDouble179(7) = 0.000000
arrayOfVariantOfDouble179(8) = 1.000000
arrayOfVariantOfDouble179(9) = 3.500915
arrayOfVariantOfDouble179(10) = 0.000000
arrayOfVariantOfDouble179(11) = 0.000000
move2.Apply arrayOfVariantOfDouble179

Set move2 = product4.Move

Set move2 = move2.MovableObject

Dim arrayOfVariantOfDouble180(11)
arrayOfVariantOfDouble180(0) = 1.000000
arrayOfVariantOfDouble180(1) = 0.000000
arrayOfVariantOfDouble180(2) = 0.000000
arrayOfVariantOfDouble180(3) = 0.000000
arrayOfVariantOfDouble180(4) = 1.000000
arrayOfVariantOfDouble180(5) = 0.000000
arrayOfVariantOfDouble180(6) = 0.000000
arrayOfVariantOfDouble180(7) = 0.000000
arrayOfVariantOfDouble180(8) = 1.000000
arrayOfVariantOfDouble180(9) = 2.429244
arrayOfVariantOfDouble180(10) = 0.000000
arrayOfVariantOfDouble180(11) = 0.000000
move2.Apply arrayOfVariantOfDouble180

Set move2 = product4.Move

Set move2 = move2.MovableObject

Dim arrayOfVariantOfDouble181(11)
arrayOfVariantOfDouble181(0) = 1.000000
arrayOfVariantOfDouble181(1) = 0.000000
arrayOfVariantOfDouble181(2) = 0.000000
arrayOfVariantOfDouble181(3) = 0.000000
arrayOfVariantOfDouble181(4) = 1.000000
arrayOfVariantOfDouble181(5) = 0.000000
arrayOfVariantOfDouble181(6) = 0.000000
arrayOfVariantOfDouble181(7) = 0.000000
arrayOfVariantOfDouble181(8) = 1.000000
arrayOfVariantOfDouble181(9) = 3.596231
arrayOfVariantOfDouble181(10) = 0.000000
arrayOfVariantOfDouble181(11) = 0.000000
move2.Apply arrayOfVariantOfDouble181

Set move2 = product4.Move

Set move2 = move2.MovableObject

Dim arrayOfVariantOfDouble182(11)
arrayOfVariantOfDouble182(0) = 1.000000
arrayOfVariantOfDouble182(1) = 0.000000
arrayOfVariantOfDouble182(2) = 0.000000
arrayOfVariantOfDouble182(3) = 0.000000
arrayOfVariantOfDouble182(4) = 1.000000
arrayOfVariantOfDouble182(5) = 0.000000
arrayOfVariantOfDouble182(6) = 0.000000
arrayOfVariantOfDouble182(7) = 0.000000
arrayOfVariantOfDouble182(8) = 1.000000
arrayOfVariantOfDouble182(9) = 5.346682
arrayOfVariantOfDouble182(10) = 0.000000
arrayOfVariantOfDouble182(11) = 0.000000
move2.Apply arrayOfVariantOfDouble182

Set move2 = product4.Move

Set move2 = move2.MovableObject

Dim arrayOfVariantOfDouble183(11)
arrayOfVariantOfDouble183(0) = 1.000000
arrayOfVariantOfDouble183(1) = 0.000000
arrayOfVariantOfDouble183(2) = 0.000000
arrayOfVariantOfDouble183(3) = 0.000000
arrayOfVariantOfDouble183(4) = 1.000000
arrayOfVariantOfDouble183(5) = 0.000000
arrayOfVariantOfDouble183(6) = 0.000000
arrayOfVariantOfDouble183(7) = 0.000000
arrayOfVariantOfDouble183(8) = 1.000000
arrayOfVariantOfDouble183(9) = 3.596220
arrayOfVariantOfDouble183(10) = 0.000000
arrayOfVariantOfDouble183(11) = 0.000000
move2.Apply arrayOfVariantOfDouble183

Set move2 = product4.Move

Set move2 = move2.MovableObject

Dim arrayOfVariantOfDouble184(11)
arrayOfVariantOfDouble184(0) = 1.000000
arrayOfVariantOfDouble184(1) = 0.000000
arrayOfVariantOfDouble184(2) = 0.000000
arrayOfVariantOfDouble184(3) = 0.000000
arrayOfVariantOfDouble184(4) = 1.000000
arrayOfVariantOfDouble184(5) = 0.000000
arrayOfVariantOfDouble184(6) = 0.000000
arrayOfVariantOfDouble184(7) = 0.000000
arrayOfVariantOfDouble184(8) = 1.000000
arrayOfVariantOfDouble184(9) = 2.333940
arrayOfVariantOfDouble184(10) = 0.000000
arrayOfVariantOfDouble184(11) = 0.000000
move2.Apply arrayOfVariantOfDouble184

Set move2 = product4.Move

Set move2 = move2.MovableObject

Dim arrayOfVariantOfDouble185(11)
arrayOfVariantOfDouble185(0) = 1.000000
arrayOfVariantOfDouble185(1) = 0.000000
arrayOfVariantOfDouble185(2) = 0.000000
arrayOfVariantOfDouble185(3) = 0.000000
arrayOfVariantOfDouble185(4) = 1.000000
arrayOfVariantOfDouble185(5) = 0.000000
arrayOfVariantOfDouble185(6) = 0.000000
arrayOfVariantOfDouble185(7) = 0.000000
arrayOfVariantOfDouble185(8) = 1.000000
arrayOfVariantOfDouble185(9) = 4.763195
arrayOfVariantOfDouble185(10) = 0.000000
arrayOfVariantOfDouble185(11) = 0.000000
move2.Apply arrayOfVariantOfDouble185

Set move2 = product4.Move

Set move2 = move2.MovableObject

Dim arrayOfVariantOfDouble186(11)
arrayOfVariantOfDouble186(0) = 1.000000
arrayOfVariantOfDouble186(1) = 0.000000
arrayOfVariantOfDouble186(2) = 0.000000
arrayOfVariantOfDouble186(3) = 0.000000
arrayOfVariantOfDouble186(4) = 1.000000
arrayOfVariantOfDouble186(5) = 0.000000
arrayOfVariantOfDouble186(6) = 0.000000
arrayOfVariantOfDouble186(7) = 0.000000
arrayOfVariantOfDouble186(8) = 1.000000
arrayOfVariantOfDouble186(9) = 1.845766
arrayOfVariantOfDouble186(10) = 0.000000
arrayOfVariantOfDouble186(11) = 0.000000
move2.Apply arrayOfVariantOfDouble186

Set move2 = product4.Move

Set move2 = move2.MovableObject

Dim arrayOfVariantOfDouble187(11)
arrayOfVariantOfDouble187(0) = 1.000000
arrayOfVariantOfDouble187(1) = 0.000000
arrayOfVariantOfDouble187(2) = 0.000000
arrayOfVariantOfDouble187(3) = 0.000000
arrayOfVariantOfDouble187(4) = 1.000000
arrayOfVariantOfDouble187(5) = 0.000000
arrayOfVariantOfDouble187(6) = 0.000000
arrayOfVariantOfDouble187(7) = 0.000000
arrayOfVariantOfDouble187(8) = 1.000000
arrayOfVariantOfDouble187(9) = 2.917429
arrayOfVariantOfDouble187(10) = 0.000000
arrayOfVariantOfDouble187(11) = 0.000000
move2.Apply arrayOfVariantOfDouble187

Set move2 = product4.Move

Set move2 = move2.MovableObject

Dim arrayOfVariantOfDouble188(11)
arrayOfVariantOfDouble188(0) = 1.000000
arrayOfVariantOfDouble188(1) = 0.000000
arrayOfVariantOfDouble188(2) = 0.000000
arrayOfVariantOfDouble188(3) = 0.000000
arrayOfVariantOfDouble188(4) = 1.000000
arrayOfVariantOfDouble188(5) = 0.000000
arrayOfVariantOfDouble188(6) = 0.000000
arrayOfVariantOfDouble188(7) = 0.000000
arrayOfVariantOfDouble188(8) = 1.000000
arrayOfVariantOfDouble188(9) = 4.179706
arrayOfVariantOfDouble188(10) = 0.000000
arrayOfVariantOfDouble188(11) = 0.000000
move2.Apply arrayOfVariantOfDouble188

Set move2 = product4.Move

Set move2 = move2.MovableObject

Dim arrayOfVariantOfDouble189(11)
arrayOfVariantOfDouble189(0) = 1.000000
arrayOfVariantOfDouble189(1) = 0.000000
arrayOfVariantOfDouble189(2) = 0.000000
arrayOfVariantOfDouble189(3) = 0.000000
arrayOfVariantOfDouble189(4) = 1.000000
arrayOfVariantOfDouble189(5) = 0.000000
arrayOfVariantOfDouble189(6) = 0.000000
arrayOfVariantOfDouble189(7) = 0.000000
arrayOfVariantOfDouble189(8) = 1.000000
arrayOfVariantOfDouble189(9) = 3.012744
arrayOfVariantOfDouble189(10) = 0.000000
arrayOfVariantOfDouble189(11) = 0.000000
move2.Apply arrayOfVariantOfDouble189

Set move2 = product4.Move

Set move2 = move2.MovableObject

Dim arrayOfVariantOfDouble190(11)
arrayOfVariantOfDouble190(0) = 1.000000
arrayOfVariantOfDouble190(1) = 0.000000
arrayOfVariantOfDouble190(2) = 0.000000
arrayOfVariantOfDouble190(3) = 0.000000
arrayOfVariantOfDouble190(4) = 1.000000
arrayOfVariantOfDouble190(5) = 0.000000
arrayOfVariantOfDouble190(6) = 0.000000
arrayOfVariantOfDouble190(7) = 0.000000
arrayOfVariantOfDouble190(8) = 1.000000
arrayOfVariantOfDouble190(9) = 1.750450
arrayOfVariantOfDouble190(10) = 0.000000
arrayOfVariantOfDouble190(11) = 0.000000
move2.Apply arrayOfVariantOfDouble190

Set move2 = product4.Move

Set move2 = move2.MovableObject

Dim arrayOfVariantOfDouble191(11)
arrayOfVariantOfDouble191(0) = 1.000000
arrayOfVariantOfDouble191(1) = 0.000000
arrayOfVariantOfDouble191(2) = 0.000000
arrayOfVariantOfDouble191(3) = 0.000000
arrayOfVariantOfDouble191(4) = 1.000000
arrayOfVariantOfDouble191(5) = 0.000000
arrayOfVariantOfDouble191(6) = 0.000000
arrayOfVariantOfDouble191(7) = 0.000000
arrayOfVariantOfDouble191(8) = 1.000000
arrayOfVariantOfDouble191(9) = 4.667880
arrayOfVariantOfDouble191(10) = 0.000000
arrayOfVariantOfDouble191(11) = 0.000000
move2.Apply arrayOfVariantOfDouble191

Set move2 = product4.Move

Set move2 = move2.MovableObject

Dim arrayOfVariantOfDouble192(11)
arrayOfVariantOfDouble192(0) = 1.000000
arrayOfVariantOfDouble192(1) = 0.000000
arrayOfVariantOfDouble192(2) = 0.000000
arrayOfVariantOfDouble192(3) = 0.000000
arrayOfVariantOfDouble192(4) = 1.000000
arrayOfVariantOfDouble192(5) = 0.000000
arrayOfVariantOfDouble192(6) = 0.000000
arrayOfVariantOfDouble192(7) = 0.000000
arrayOfVariantOfDouble192(8) = 1.000000
arrayOfVariantOfDouble192(9) = 3.596220
arrayOfVariantOfDouble192(10) = 0.000000
arrayOfVariantOfDouble192(11) = 0.000000
move2.Apply arrayOfVariantOfDouble192

Set move2 = product4.Move

Set move2 = move2.MovableObject

Dim arrayOfVariantOfDouble193(11)
arrayOfVariantOfDouble193(0) = 1.000000
arrayOfVariantOfDouble193(1) = 0.000000
arrayOfVariantOfDouble193(2) = 0.000000
arrayOfVariantOfDouble193(3) = 0.000000
arrayOfVariantOfDouble193(4) = 1.000000
arrayOfVariantOfDouble193(5) = 0.000000
arrayOfVariantOfDouble193(6) = 0.000000
arrayOfVariantOfDouble193(7) = 0.000000
arrayOfVariantOfDouble193(8) = 1.000000
arrayOfVariantOfDouble193(9) = 4.179705
arrayOfVariantOfDouble193(10) = 0.000000
arrayOfVariantOfDouble193(11) = 0.000000
move2.Apply arrayOfVariantOfDouble193

Set move2 = product4.Move

Set move2 = move2.MovableObject

Dim arrayOfVariantOfDouble194(11)
arrayOfVariantOfDouble194(0) = 1.000000
arrayOfVariantOfDouble194(1) = 0.000000
arrayOfVariantOfDouble194(2) = 0.000000
arrayOfVariantOfDouble194(3) = 0.000000
arrayOfVariantOfDouble194(4) = 1.000000
arrayOfVariantOfDouble194(5) = 0.000000
arrayOfVariantOfDouble194(6) = 0.000000
arrayOfVariantOfDouble194(7) = 0.000000
arrayOfVariantOfDouble194(8) = 1.000000
arrayOfVariantOfDouble194(9) = 2.917429
arrayOfVariantOfDouble194(10) = 0.000000
arrayOfVariantOfDouble194(11) = 0.000000
move2.Apply arrayOfVariantOfDouble194

Set move2 = product4.Move

Set move2 = move2.MovableObject

Dim arrayOfVariantOfDouble195(11)
arrayOfVariantOfDouble195(0) = 1.000000
arrayOfVariantOfDouble195(1) = 0.000000
arrayOfVariantOfDouble195(2) = 0.000000
arrayOfVariantOfDouble195(3) = 0.000000
arrayOfVariantOfDouble195(4) = 1.000000
arrayOfVariantOfDouble195(5) = 0.000000
arrayOfVariantOfDouble195(6) = 0.000000
arrayOfVariantOfDouble195(7) = 0.000000
arrayOfVariantOfDouble195(8) = 1.000000
arrayOfVariantOfDouble195(9) = 4.179718
arrayOfVariantOfDouble195(10) = 0.000000
arrayOfVariantOfDouble195(11) = 0.000000
move2.Apply arrayOfVariantOfDouble195

Set move2 = product4.Move

Set move2 = move2.MovableObject

Dim arrayOfVariantOfDouble196(11)
arrayOfVariantOfDouble196(0) = 1.000000
arrayOfVariantOfDouble196(1) = 0.000000
arrayOfVariantOfDouble196(2) = 0.000000
arrayOfVariantOfDouble196(3) = 0.000000
arrayOfVariantOfDouble196(4) = 1.000000
arrayOfVariantOfDouble196(5) = 0.000000
arrayOfVariantOfDouble196(6) = 0.000000
arrayOfVariantOfDouble196(7) = 0.000000
arrayOfVariantOfDouble196(8) = 1.000000
arrayOfVariantOfDouble196(9) = 3.012733
arrayOfVariantOfDouble196(10) = 0.000000
arrayOfVariantOfDouble196(11) = 0.000000
move2.Apply arrayOfVariantOfDouble196

Set move2 = product4.Move

Set move2 = move2.MovableObject

Dim arrayOfVariantOfDouble197(11)
arrayOfVariantOfDouble197(0) = 1.000000
arrayOfVariantOfDouble197(1) = 0.000000
arrayOfVariantOfDouble197(2) = 0.000000
arrayOfVariantOfDouble197(3) = 0.000000
arrayOfVariantOfDouble197(4) = 1.000000
arrayOfVariantOfDouble197(5) = 0.000000
arrayOfVariantOfDouble197(6) = 0.000000
arrayOfVariantOfDouble197(7) = 0.000000
arrayOfVariantOfDouble197(8) = 1.000000
arrayOfVariantOfDouble197(9) = 3.500917
arrayOfVariantOfDouble197(10) = 0.000000
arrayOfVariantOfDouble197(11) = 0.000000
move2.Apply arrayOfVariantOfDouble197

Set move2 = product4.Move

Set move2 = move2.MovableObject

Dim arrayOfVariantOfDouble198(11)
arrayOfVariantOfDouble198(0) = 1.000000
arrayOfVariantOfDouble198(1) = 0.000000
arrayOfVariantOfDouble198(2) = 0.000000
arrayOfVariantOfDouble198(3) = 0.000000
arrayOfVariantOfDouble198(4) = 1.000000
arrayOfVariantOfDouble198(5) = 0.000000
arrayOfVariantOfDouble198(6) = 0.000000
arrayOfVariantOfDouble198(7) = 0.000000
arrayOfVariantOfDouble198(8) = 1.000000
arrayOfVariantOfDouble198(9) = 2.333937
arrayOfVariantOfDouble198(10) = 0.000000
arrayOfVariantOfDouble198(11) = 0.000000
move2.Apply arrayOfVariantOfDouble198

Set move2 = product4.Move

Set move2 = move2.MovableObject

Dim arrayOfVariantOfDouble199(11)
arrayOfVariantOfDouble199(0) = 1.000000
arrayOfVariantOfDouble199(1) = 0.000000
arrayOfVariantOfDouble199(2) = 0.000000
arrayOfVariantOfDouble199(3) = 0.000000
arrayOfVariantOfDouble199(4) = 1.000000
arrayOfVariantOfDouble199(5) = 0.000000
arrayOfVariantOfDouble199(6) = 0.000000
arrayOfVariantOfDouble199(7) = 0.000000
arrayOfVariantOfDouble199(8) = 1.000000
arrayOfVariantOfDouble199(9) = 1.845770
arrayOfVariantOfDouble199(10) = 0.000000
arrayOfVariantOfDouble199(11) = 0.000000
move2.Apply arrayOfVariantOfDouble199

Set move2 = product4.Move

Set move2 = move2.MovableObject

Dim arrayOfVariantOfDouble200(11)
arrayOfVariantOfDouble200(0) = 1.000000
arrayOfVariantOfDouble200(1) = 0.000000
arrayOfVariantOfDouble200(2) = 0.000000
arrayOfVariantOfDouble200(3) = 0.000000
arrayOfVariantOfDouble200(4) = 1.000000
arrayOfVariantOfDouble200(5) = 0.000000
arrayOfVariantOfDouble200(6) = 0.000000
arrayOfVariantOfDouble200(7) = 0.000000
arrayOfVariantOfDouble200(8) = 1.000000
arrayOfVariantOfDouble200(9) = 2.917425
arrayOfVariantOfDouble200(10) = 0.000000
arrayOfVariantOfDouble200(11) = 0.000000
move2.Apply arrayOfVariantOfDouble200

Set move2 = product4.Move

Set move2 = move2.MovableObject

Dim arrayOfVariantOfDouble201(11)
arrayOfVariantOfDouble201(0) = 1.000000
arrayOfVariantOfDouble201(1) = 0.000000
arrayOfVariantOfDouble201(2) = 0.000000
arrayOfVariantOfDouble201(3) = 0.000000
arrayOfVariantOfDouble201(4) = 1.000000
arrayOfVariantOfDouble201(5) = 0.000000
arrayOfVariantOfDouble201(6) = 0.000000
arrayOfVariantOfDouble201(7) = 0.000000
arrayOfVariantOfDouble201(8) = 1.000000
arrayOfVariantOfDouble201(9) = 3.012733
arrayOfVariantOfDouble201(10) = 0.000000
arrayOfVariantOfDouble201(11) = 0.000000
move2.Apply arrayOfVariantOfDouble201

Set move2 = product4.Move

Set move2 = move2.MovableObject

Dim arrayOfVariantOfDouble202(11)
arrayOfVariantOfDouble202(0) = 1.000000
arrayOfVariantOfDouble202(1) = 0.000000
arrayOfVariantOfDouble202(2) = 0.000000
arrayOfVariantOfDouble202(3) = 0.000000
arrayOfVariantOfDouble202(4) = 1.000000
arrayOfVariantOfDouble202(5) = 0.000000
arrayOfVariantOfDouble202(6) = 0.000000
arrayOfVariantOfDouble202(7) = 0.000000
arrayOfVariantOfDouble202(8) = 1.000000
arrayOfVariantOfDouble202(9) = 2.333952
arrayOfVariantOfDouble202(10) = 0.000000
arrayOfVariantOfDouble202(11) = 0.000000
move2.Apply arrayOfVariantOfDouble202

Set move2 = product4.Move

Set move2 = move2.MovableObject

Dim arrayOfVariantOfDouble203(11)
arrayOfVariantOfDouble203(0) = 1.000000
arrayOfVariantOfDouble203(1) = 0.000000
arrayOfVariantOfDouble203(2) = 0.000000
arrayOfVariantOfDouble203(3) = 0.000000
arrayOfVariantOfDouble203(4) = 1.000000
arrayOfVariantOfDouble203(5) = 0.000000
arrayOfVariantOfDouble203(6) = 0.000000
arrayOfVariantOfDouble203(7) = 0.000000
arrayOfVariantOfDouble203(8) = 1.000000
arrayOfVariantOfDouble203(9) = 2.333929
arrayOfVariantOfDouble203(10) = 0.000000
arrayOfVariantOfDouble203(11) = 0.000000
move2.Apply arrayOfVariantOfDouble203

Set move2 = product4.Move

Set move2 = move2.MovableObject

Dim arrayOfVariantOfDouble204(11)
arrayOfVariantOfDouble204(0) = 1.000000
arrayOfVariantOfDouble204(1) = 0.000000
arrayOfVariantOfDouble204(2) = 0.000000
arrayOfVariantOfDouble204(3) = 0.000000
arrayOfVariantOfDouble204(4) = 1.000000
arrayOfVariantOfDouble204(5) = 0.000000
arrayOfVariantOfDouble204(6) = 0.000000
arrayOfVariantOfDouble204(7) = 0.000000
arrayOfVariantOfDouble204(8) = 1.000000
arrayOfVariantOfDouble204(9) = 1.750463
arrayOfVariantOfDouble204(10) = 0.000000
arrayOfVariantOfDouble204(11) = 0.000000
move2.Apply arrayOfVariantOfDouble204

Set move2 = product4.Move

Set move2 = move2.MovableObject

Dim arrayOfVariantOfDouble205(11)
arrayOfVariantOfDouble205(0) = 1.000000
arrayOfVariantOfDouble205(1) = 0.000000
arrayOfVariantOfDouble205(2) = 0.000000
arrayOfVariantOfDouble205(3) = 0.000000
arrayOfVariantOfDouble205(4) = 1.000000
arrayOfVariantOfDouble205(5) = 0.000000
arrayOfVariantOfDouble205(6) = 0.000000
arrayOfVariantOfDouble205(7) = 0.000000
arrayOfVariantOfDouble205(8) = 1.000000
arrayOfVariantOfDouble205(9) = 3.012732
arrayOfVariantOfDouble205(10) = 0.000000
arrayOfVariantOfDouble205(11) = 0.000000
move2.Apply arrayOfVariantOfDouble205

Set move2 = product4.Move

Set move2 = move2.MovableObject

Dim arrayOfVariantOfDouble206(11)
arrayOfVariantOfDouble206(0) = 1.000000
arrayOfVariantOfDouble206(1) = 0.000000
arrayOfVariantOfDouble206(2) = 0.000000
arrayOfVariantOfDouble206(3) = 0.000000
arrayOfVariantOfDouble206(4) = 1.000000
arrayOfVariantOfDouble206(5) = 0.000000
arrayOfVariantOfDouble206(6) = 0.000000
arrayOfVariantOfDouble206(7) = 0.000000
arrayOfVariantOfDouble206(8) = 1.000000
arrayOfVariantOfDouble206(9) = 1.166974
arrayOfVariantOfDouble206(10) = 0.000000
arrayOfVariantOfDouble206(11) = 0.000000
move2.Apply arrayOfVariantOfDouble206

Set move2 = product4.Move

Set move2 = move2.MovableObject

Dim arrayOfVariantOfDouble207(11)
arrayOfVariantOfDouble207(0) = 1.000000
arrayOfVariantOfDouble207(1) = 0.000000
arrayOfVariantOfDouble207(2) = 0.000000
arrayOfVariantOfDouble207(3) = 0.000000
arrayOfVariantOfDouble207(4) = 1.000000
arrayOfVariantOfDouble207(5) = 0.000000
arrayOfVariantOfDouble207(6) = 0.000000
arrayOfVariantOfDouble207(7) = 0.000000
arrayOfVariantOfDouble207(8) = 1.000000
arrayOfVariantOfDouble207(9) = 1.750455
arrayOfVariantOfDouble207(10) = 0.000000
arrayOfVariantOfDouble207(11) = 0.000000
move2.Apply arrayOfVariantOfDouble207

Set move2 = product4.Move

Set move2 = move2.MovableObject

Dim arrayOfVariantOfDouble208(11)
arrayOfVariantOfDouble208(0) = 1.000000
arrayOfVariantOfDouble208(1) = 0.000000
arrayOfVariantOfDouble208(2) = 0.000000
arrayOfVariantOfDouble208(3) = 0.000000
arrayOfVariantOfDouble208(4) = 1.000000
arrayOfVariantOfDouble208(5) = 0.000000
arrayOfVariantOfDouble208(6) = 0.000000
arrayOfVariantOfDouble208(7) = 0.000000
arrayOfVariantOfDouble208(8) = 1.000000
arrayOfVariantOfDouble208(9) = 2.333940
arrayOfVariantOfDouble208(10) = 0.000000
arrayOfVariantOfDouble208(11) = 0.000000
move2.Apply arrayOfVariantOfDouble208

Set move2 = product4.Move

Set move2 = move2.MovableObject

Dim arrayOfVariantOfDouble209(11)
arrayOfVariantOfDouble209(0) = 1.000000
arrayOfVariantOfDouble209(1) = 0.000000
arrayOfVariantOfDouble209(2) = 0.000000
arrayOfVariantOfDouble209(3) = 0.000000
arrayOfVariantOfDouble209(4) = 1.000000
arrayOfVariantOfDouble209(5) = 0.000000
arrayOfVariantOfDouble209(6) = 0.000000
arrayOfVariantOfDouble209(7) = 0.000000
arrayOfVariantOfDouble209(8) = 1.000000
arrayOfVariantOfDouble209(9) = 1.166974
arrayOfVariantOfDouble209(10) = 0.000000
arrayOfVariantOfDouble209(11) = 0.000000
move2.Apply arrayOfVariantOfDouble209

Set move2 = product4.Move

Set move2 = move2.MovableObject

Dim arrayOfVariantOfDouble210(11)
arrayOfVariantOfDouble210(0) = 1.000000
arrayOfVariantOfDouble210(1) = 0.000000
arrayOfVariantOfDouble210(2) = 0.000000
arrayOfVariantOfDouble210(3) = 0.000000
arrayOfVariantOfDouble210(4) = 1.000000
arrayOfVariantOfDouble210(5) = 0.000000
arrayOfVariantOfDouble210(6) = 0.000000
arrayOfVariantOfDouble210(7) = 0.000000
arrayOfVariantOfDouble210(8) = 1.000000
arrayOfVariantOfDouble210(9) = 1.166965
arrayOfVariantOfDouble210(10) = 0.000000
arrayOfVariantOfDouble210(11) = 0.000000
move2.Apply arrayOfVariantOfDouble210

Set move2 = product4.Move

Set move2 = move2.MovableObject

Dim arrayOfVariantOfDouble211(11)
arrayOfVariantOfDouble211(0) = 1.000000
arrayOfVariantOfDouble211(1) = 0.000000
arrayOfVariantOfDouble211(2) = 0.000000
arrayOfVariantOfDouble211(3) = 0.000000
arrayOfVariantOfDouble211(4) = 1.000000
arrayOfVariantOfDouble211(5) = 0.000000
arrayOfVariantOfDouble211(6) = 0.000000
arrayOfVariantOfDouble211(7) = 0.000000
arrayOfVariantOfDouble211(8) = 1.000000
arrayOfVariantOfDouble211(9) = 1.166975
arrayOfVariantOfDouble211(10) = 0.000000
arrayOfVariantOfDouble211(11) = 0.000000
move2.Apply arrayOfVariantOfDouble211

Set move2 = product4.Move

Set move2 = move2.MovableObject

Dim arrayOfVariantOfDouble212(11)
arrayOfVariantOfDouble212(0) = 1.000000
arrayOfVariantOfDouble212(1) = 0.000000
arrayOfVariantOfDouble212(2) = 0.000000
arrayOfVariantOfDouble212(3) = 0.000000
arrayOfVariantOfDouble212(4) = 1.000000
arrayOfVariantOfDouble212(5) = 0.000000
arrayOfVariantOfDouble212(6) = 0.000000
arrayOfVariantOfDouble212(7) = 0.000000
arrayOfVariantOfDouble212(8) = 1.000000
arrayOfVariantOfDouble212(9) = 1.166977
arrayOfVariantOfDouble212(10) = 0.000000
arrayOfVariantOfDouble212(11) = 0.000000
move2.Apply arrayOfVariantOfDouble212

Set move2 = product4.Move

Set move2 = move2.MovableObject

Dim arrayOfVariantOfDouble213(11)
arrayOfVariantOfDouble213(0) = 1.000000
arrayOfVariantOfDouble213(1) = 0.000000
arrayOfVariantOfDouble213(2) = 0.000000
arrayOfVariantOfDouble213(3) = 0.000000
arrayOfVariantOfDouble213(4) = 1.000000
arrayOfVariantOfDouble213(5) = 0.000000
arrayOfVariantOfDouble213(6) = 0.000000
arrayOfVariantOfDouble213(7) = 0.000000
arrayOfVariantOfDouble213(8) = 1.000000
arrayOfVariantOfDouble213(9) = 1.166962
arrayOfVariantOfDouble213(10) = 0.000000
arrayOfVariantOfDouble213(11) = 0.000000
move2.Apply arrayOfVariantOfDouble213

Set move2 = product4.Move

Set move2 = move2.MovableObject

Dim arrayOfVariantOfDouble214(11)
arrayOfVariantOfDouble214(0) = 1.000000
arrayOfVariantOfDouble214(1) = 0.000000
arrayOfVariantOfDouble214(2) = 0.000000
arrayOfVariantOfDouble214(3) = 0.000000
arrayOfVariantOfDouble214(4) = 1.000000
arrayOfVariantOfDouble214(5) = 0.000000
arrayOfVariantOfDouble214(6) = 0.000000
arrayOfVariantOfDouble214(7) = 0.000000
arrayOfVariantOfDouble214(8) = 1.000000
arrayOfVariantOfDouble214(9) = 1.166966
arrayOfVariantOfDouble214(10) = 0.000000
arrayOfVariantOfDouble214(11) = 0.000000
move2.Apply arrayOfVariantOfDouble214

Set move2 = product4.Move

Set move2 = move2.MovableObject

Dim arrayOfVariantOfDouble215(11)
arrayOfVariantOfDouble215(0) = 1.000000
arrayOfVariantOfDouble215(1) = 0.000000
arrayOfVariantOfDouble215(2) = 0.000000
arrayOfVariantOfDouble215(3) = 0.000000
arrayOfVariantOfDouble215(4) = 1.000000
arrayOfVariantOfDouble215(5) = 0.000000
arrayOfVariantOfDouble215(6) = 0.000000
arrayOfVariantOfDouble215(7) = 0.000000
arrayOfVariantOfDouble215(8) = 1.000000
arrayOfVariantOfDouble215(9) = 0.583489
arrayOfVariantOfDouble215(10) = 0.000000
arrayOfVariantOfDouble215(11) = 0.000000
move2.Apply arrayOfVariantOfDouble215

Set move2 = product4.Move

Set move2 = move2.MovableObject

Dim arrayOfVariantOfDouble216(11)
arrayOfVariantOfDouble216(0) = 1.000000
arrayOfVariantOfDouble216(1) = 0.000000
arrayOfVariantOfDouble216(2) = 0.000000
arrayOfVariantOfDouble216(3) = 0.000000
arrayOfVariantOfDouble216(4) = 1.000000
arrayOfVariantOfDouble216(5) = 0.000000
arrayOfVariantOfDouble216(6) = 0.000000
arrayOfVariantOfDouble216(7) = 0.000000
arrayOfVariantOfDouble216(8) = 1.000000
arrayOfVariantOfDouble216(9) = 1.166975
arrayOfVariantOfDouble216(10) = 0.000000
arrayOfVariantOfDouble216(11) = 0.000000
move2.Apply arrayOfVariantOfDouble216

Set move2 = product4.Move

Set move2 = move2.MovableObject

Dim arrayOfVariantOfDouble217(11)
arrayOfVariantOfDouble217(0) = 1.000000
arrayOfVariantOfDouble217(1) = 0.000000
arrayOfVariantOfDouble217(2) = 0.000000
arrayOfVariantOfDouble217(3) = 0.000000
arrayOfVariantOfDouble217(4) = 1.000000
arrayOfVariantOfDouble217(5) = 0.000000
arrayOfVariantOfDouble217(6) = 0.000000
arrayOfVariantOfDouble217(7) = 0.000000
arrayOfVariantOfDouble217(8) = 1.000000
arrayOfVariantOfDouble217(9) = 1.166967
arrayOfVariantOfDouble217(10) = 0.000000
arrayOfVariantOfDouble217(11) = 0.000000
move2.Apply arrayOfVariantOfDouble217

Set move2 = product4.Move

Set move2 = move2.MovableObject

Dim arrayOfVariantOfDouble218(11)
arrayOfVariantOfDouble218(0) = 1.000000
arrayOfVariantOfDouble218(1) = 0.000000
arrayOfVariantOfDouble218(2) = 0.000000
arrayOfVariantOfDouble218(3) = 0.000000
arrayOfVariantOfDouble218(4) = 1.000000
arrayOfVariantOfDouble218(5) = 0.000000
arrayOfVariantOfDouble218(6) = 0.000000
arrayOfVariantOfDouble218(7) = 0.000000
arrayOfVariantOfDouble218(8) = 1.000000
arrayOfVariantOfDouble218(9) = 1.262276
arrayOfVariantOfDouble218(10) = 0.000000
arrayOfVariantOfDouble218(11) = 0.000000
move2.Apply arrayOfVariantOfDouble218

Set move2 = product4.Move

Set move2 = move2.MovableObject

Dim arrayOfVariantOfDouble219(11)
arrayOfVariantOfDouble219(0) = 1.000000
arrayOfVariantOfDouble219(1) = 0.000000
arrayOfVariantOfDouble219(2) = 0.000000
arrayOfVariantOfDouble219(3) = 0.000000
arrayOfVariantOfDouble219(4) = 1.000000
arrayOfVariantOfDouble219(5) = 0.000000
arrayOfVariantOfDouble219(6) = 0.000000
arrayOfVariantOfDouble219(7) = 0.000000
arrayOfVariantOfDouble219(8) = 1.000000
arrayOfVariantOfDouble219(9) = 0.583490
arrayOfVariantOfDouble219(10) = 0.000000
arrayOfVariantOfDouble219(11) = 0.000000
move2.Apply arrayOfVariantOfDouble219

Set move2 = product4.Move

Set move2 = move2.MovableObject

Dim arrayOfVariantOfDouble220(11)
arrayOfVariantOfDouble220(0) = 1.000000
arrayOfVariantOfDouble220(1) = 0.000000
arrayOfVariantOfDouble220(2) = 0.000000
arrayOfVariantOfDouble220(3) = 0.000000
arrayOfVariantOfDouble220(4) = 1.000000
arrayOfVariantOfDouble220(5) = 0.000000
arrayOfVariantOfDouble220(6) = 0.000000
arrayOfVariantOfDouble220(7) = 0.000000
arrayOfVariantOfDouble220(8) = 1.000000
arrayOfVariantOfDouble220(9) = 0.583489
arrayOfVariantOfDouble220(10) = 0.000000
arrayOfVariantOfDouble220(11) = 0.000000
move2.Apply arrayOfVariantOfDouble220

Set move2 = product4.Move

Set move2 = move2.MovableObject

Dim arrayOfVariantOfDouble221(11)
arrayOfVariantOfDouble221(0) = 1.000000
arrayOfVariantOfDouble221(1) = 0.000000
arrayOfVariantOfDouble221(2) = 0.000000
arrayOfVariantOfDouble221(3) = 0.000000
arrayOfVariantOfDouble221(4) = 1.000000
arrayOfVariantOfDouble221(5) = 0.000000
arrayOfVariantOfDouble221(6) = 0.000000
arrayOfVariantOfDouble221(7) = 0.000000
arrayOfVariantOfDouble221(8) = 1.000000
arrayOfVariantOfDouble221(9) = 0.583485
arrayOfVariantOfDouble221(10) = 0.000000
arrayOfVariantOfDouble221(11) = 0.000000
move2.Apply arrayOfVariantOfDouble221

Set move2 = product4.Move

Set move2 = move2.MovableObject

Dim arrayOfVariantOfDouble222(11)
arrayOfVariantOfDouble222(0) = 1.000000
arrayOfVariantOfDouble222(1) = 0.000000
arrayOfVariantOfDouble222(2) = 0.000000
arrayOfVariantOfDouble222(3) = 0.000000
arrayOfVariantOfDouble222(4) = 1.000000
arrayOfVariantOfDouble222(5) = 0.000000
arrayOfVariantOfDouble222(6) = 0.000000
arrayOfVariantOfDouble222(7) = 0.000000
arrayOfVariantOfDouble222(8) = 1.000000
arrayOfVariantOfDouble222(9) = 0.583477
arrayOfVariantOfDouble222(10) = 0.000000
arrayOfVariantOfDouble222(11) = 0.000000
move2.Apply arrayOfVariantOfDouble222

Set move2 = product4.Move

Set move2 = move2.MovableObject

Dim arrayOfVariantOfDouble223(11)
arrayOfVariantOfDouble223(0) = 1.000000
arrayOfVariantOfDouble223(1) = 0.000000
arrayOfVariantOfDouble223(2) = 0.000000
arrayOfVariantOfDouble223(3) = 0.000000
arrayOfVariantOfDouble223(4) = 1.000000
arrayOfVariantOfDouble223(5) = 0.000000
arrayOfVariantOfDouble223(6) = 0.000000
arrayOfVariantOfDouble223(7) = 0.000000
arrayOfVariantOfDouble223(8) = 1.000000
arrayOfVariantOfDouble223(9) = 1.166978
arrayOfVariantOfDouble223(10) = 0.000000
arrayOfVariantOfDouble223(11) = 0.000000
move2.Apply arrayOfVariantOfDouble223

Set move2 = product4.Move

Set move2 = move2.MovableObject

Dim arrayOfVariantOfDouble224(11)
arrayOfVariantOfDouble224(0) = 1.000000
arrayOfVariantOfDouble224(1) = 0.000000
arrayOfVariantOfDouble224(2) = 0.000000
arrayOfVariantOfDouble224(3) = 0.000000
arrayOfVariantOfDouble224(4) = 1.000000
arrayOfVariantOfDouble224(5) = 0.000000
arrayOfVariantOfDouble224(6) = 0.000000
arrayOfVariantOfDouble224(7) = 0.000000
arrayOfVariantOfDouble224(8) = 1.000000
arrayOfVariantOfDouble224(9) = -0.583478
arrayOfVariantOfDouble224(10) = 0.000000
arrayOfVariantOfDouble224(11) = 0.000000
move2.Apply arrayOfVariantOfDouble224

Set move2 = product4.Move

Set move2 = move2.MovableObject

Dim arrayOfVariantOfDouble225(11)
arrayOfVariantOfDouble225(0) = 1.000000
arrayOfVariantOfDouble225(1) = 0.000000
arrayOfVariantOfDouble225(2) = 0.000000
arrayOfVariantOfDouble225(3) = 0.000000
arrayOfVariantOfDouble225(4) = 1.000000
arrayOfVariantOfDouble225(5) = 0.000000
arrayOfVariantOfDouble225(6) = 0.000000
arrayOfVariantOfDouble225(7) = 0.000000
arrayOfVariantOfDouble225(8) = 1.000000
arrayOfVariantOfDouble225(9) = 0.095304
arrayOfVariantOfDouble225(10) = 0.000000
arrayOfVariantOfDouble225(11) = 0.000000
move2.Apply arrayOfVariantOfDouble225

Set move2 = product4.Move

Set move2 = move2.MovableObject

Dim arrayOfVariantOfDouble226(11)
arrayOfVariantOfDouble226(0) = 1.000000
arrayOfVariantOfDouble226(1) = 0.000000
arrayOfVariantOfDouble226(2) = 0.000000
arrayOfVariantOfDouble226(3) = 0.000000
arrayOfVariantOfDouble226(4) = 1.000000
arrayOfVariantOfDouble226(5) = 0.000000
arrayOfVariantOfDouble226(6) = 0.000000
arrayOfVariantOfDouble226(7) = 0.000000
arrayOfVariantOfDouble226(8) = 1.000000
arrayOfVariantOfDouble226(9) = -0.583489
arrayOfVariantOfDouble226(10) = 0.000000
arrayOfVariantOfDouble226(11) = 0.000000
move2.Apply arrayOfVariantOfDouble226

Set move2 = product4.Move

Set move2 = move2.MovableObject

Dim arrayOfVariantOfDouble227(11)
arrayOfVariantOfDouble227(0) = 1.000000
arrayOfVariantOfDouble227(1) = 0.000000
arrayOfVariantOfDouble227(2) = 0.000000
arrayOfVariantOfDouble227(3) = 0.000000
arrayOfVariantOfDouble227(4) = 1.000000
arrayOfVariantOfDouble227(5) = 0.000000
arrayOfVariantOfDouble227(6) = 0.000000
arrayOfVariantOfDouble227(7) = 0.000000
arrayOfVariantOfDouble227(8) = 1.000000
arrayOfVariantOfDouble227(9) = -0.583478
arrayOfVariantOfDouble227(10) = 0.000000
arrayOfVariantOfDouble227(11) = 0.000000
move2.Apply arrayOfVariantOfDouble227

Set constraints1 = product1.Connections("CATIAConstraints")

Dim reference24 As Reference
Set reference24 = product1.CreateReferenceFromName("A2/DM.1/!Axis:(Selection_RSur:(Face:(Brp:(Pocket.1;0:(Brp:(Sketch.2;4)));None:();Cf11:());Pocket.2_ResultOUT;Z0;G4162))")

Dim reference25 As Reference
Set reference25 = product1.CreateReferenceFromName("A2/Nut.2/!Axis:(Selection_RSur:(Face:(Brp:(Pocket.1;0:(Brp:(Sketch.2;4)));None:();Cf11:());Pocket.1_ResultOUT;Z0;G4162))")

Dim constraint14 As Constraint
Set constraint14 = constraints1.AddBiEltCst(catCstTypeOn, reference24, reference25)

Set constraints1 = product1.Connections("CATIAConstraints")

Dim reference26 As Reference
Set reference26 = product1.CreateReferenceFromName("A2/Nut.2/!Selection_RSur:(Face:(Brp:(Pad.1;2);None:();Cf11:());Pocket.1_ResultOUT;Z0;G4162)")

Dim reference27 As Reference
Set reference27 = product1.CreateReferenceFromName("A2/DM.1/!Selection_RSur:(Face:(Brp:(Pad.1;0:(Brp:(Sketch.1;13)));None:();Cf11:());Pocket.2_ResultOUT;Z0;G4162)")

Dim constraint15 As Constraint
Set constraint15 = constraints1.AddBiEltCst(catCstTypeSurfContact, reference26, reference27)

product1.Update 

Set constraints1 = product1.Connections("CATIAConstraints")

Dim reference28 As Reference
Set reference28 = product1.CreateReferenceFromName("A2/Nut.2/!Selection_RSur:(Face:(Brp:(Pad.1;0:(Brp:(Sketch.1;8)));None:();Cf11:());Pocket.1_ResultOUT;Z0;G4162)")

Dim reference29 As Reference
Set reference29 = product1.CreateReferenceFromName("A2/DM.1/!Selection_RSur:(Face:(Brp:(Pad.1;0:(Brp:(Sketch.1;12)));None:();Cf11:());Pocket.2_ResultOUT;Z0;G4162)")

Dim constraint16 As Constraint
Set constraint16 = constraints1.AddBiEltCst(catCstTypeAngle, reference28, reference29)

Dim angle2 As Dimension
Set angle2 = constraint16.Dimension

angle2.Value = 0.000000

constraint16.AngleSector = catCstAngleSector0

product1.Update 



Dim arrayOfVariantOfBSTR7(0)
arrayOfVariantOfBSTR7(0) = ".\SubAssembly\Bar.CATPart"
products1.AddComponentsFromFiles arrayOfVariantOfBSTR7, "All"

Set constraints1 = product1.Connections("CATIAConstraints")

Dim reference30 As Reference
Set reference30 = product1.CreateReferenceFromName("A2/Bar.1/!Axis:(Selection_RSur:(Face:(Brp:(Pad.1;0:(Brp:(Sketch.1;3)));None:();Cf11:());Pad.1_ResultOUT;Z0;G4162))")

Set reference19 = product1.CreateReferenceFromName("A2/DM.2/!Axis:(Selection_RSur:(Face:(Brp:(Pocket.1;0:(Brp:(Sketch.2;4)));None:();Cf11:());Pocket.2_ResultOUT;Z0;G4162))")

Dim constraint17 As Constraint
Set constraint17 = constraints1.AddBiEltCst(catCstTypeOn, reference30, reference19)

product1.Update 


Set constraints1 = product1.Connections("CATIAConstraints")

Dim reference31 As Reference
Set reference31 = product1.CreateReferenceFromName("A2/Plate.1/!Selection_RSur:(Face:(Brp:(Pad.1;0:(Brp:(Sketch.1;9)));None:();Cf11:());Pad.1_ResultOUT;Z0;G4162)")

Dim reference32 As Reference
Set reference32 = product1.CreateReferenceFromName("A2/Bar.1/!Selection_RSur:(Face:(Brp:(Pad.1;2);None:();Cf11:());Pad.1_ResultOUT;Z0;G4162)")

Dim constraint19 As Constraint
Set constraint19 = constraints1.AddBiEltCst(catCstTypeDistance, reference31, reference32)

Dim length1 As Dimension
Set length1 = constraint19.Dimension

length1.Value = 1.000000

constraint19.Orientation = catCstOrientSame

product1.Update 

length1.Value = 10.000000

constraint19.Orientation = catCstOrientSame

product1.Update 




specsAndGeomWindow1.WindowState = catWindowStateMaximized

Dim arrayOfVariantOfBSTR8(0)
arrayOfVariantOfBSTR8(0) = ".\SubAssembly\Bolt.CATPart"
products1.AddComponentsFromFiles arrayOfVariantOfBSTR8, "All"

Dim product5 As Product
Set product5 = products1.Item("Bolt.1")

Dim move3 As Move
Set move3 = product5.Move

Set move3 = move3.MovableObject

Dim arrayOfVariantOfDouble228(11)
arrayOfVariantOfDouble228(0) = 1.000000
arrayOfVariantOfDouble228(1) = 0.000000
arrayOfVariantOfDouble228(2) = 0.000000
arrayOfVariantOfDouble228(3) = 0.000000
arrayOfVariantOfDouble228(4) = 1.000000
arrayOfVariantOfDouble228(5) = 0.000000
arrayOfVariantOfDouble228(6) = 0.000000
arrayOfVariantOfDouble228(7) = 0.000000
arrayOfVariantOfDouble228(8) = 1.000000
arrayOfVariantOfDouble228(9) = -2.399349
arrayOfVariantOfDouble228(10) = 0.000000
arrayOfVariantOfDouble228(11) = 0.000000
move3.Apply arrayOfVariantOfDouble228

Set move3 = product5.Move

Set move3 = move3.MovableObject

Dim arrayOfVariantOfDouble229(11)
arrayOfVariantOfDouble229(0) = 1.000000
arrayOfVariantOfDouble229(1) = 0.000000
arrayOfVariantOfDouble229(2) = 0.000000
arrayOfVariantOfDouble229(3) = 0.000000
arrayOfVariantOfDouble229(4) = 1.000000
arrayOfVariantOfDouble229(5) = 0.000000
arrayOfVariantOfDouble229(6) = 0.000000
arrayOfVariantOfDouble229(7) = 0.000000
arrayOfVariantOfDouble229(8) = 1.000000
arrayOfVariantOfDouble229(9) = -0.372859
arrayOfVariantOfDouble229(10) = 0.000000
arrayOfVariantOfDouble229(11) = 0.000000
move3.Apply arrayOfVariantOfDouble229

Set move3 = product5.Move

Set move3 = move3.MovableObject

Dim arrayOfVariantOfDouble230(11)
arrayOfVariantOfDouble230(0) = 1.000000
arrayOfVariantOfDouble230(1) = 0.000000
arrayOfVariantOfDouble230(2) = 0.000000
arrayOfVariantOfDouble230(3) = 0.000000
arrayOfVariantOfDouble230(4) = 1.000000
arrayOfVariantOfDouble230(5) = 0.000000
arrayOfVariantOfDouble230(6) = 0.000000
arrayOfVariantOfDouble230(7) = 0.000000
arrayOfVariantOfDouble230(8) = 1.000000
arrayOfVariantOfDouble230(9) = -0.745711
arrayOfVariantOfDouble230(10) = 0.000000
arrayOfVariantOfDouble230(11) = 0.000000
move3.Apply arrayOfVariantOfDouble230

Set move3 = product5.Move

Set move3 = move3.MovableObject

Dim arrayOfVariantOfDouble231(11)
arrayOfVariantOfDouble231(0) = 1.000000
arrayOfVariantOfDouble231(1) = 0.000000
arrayOfVariantOfDouble231(2) = 0.000000
arrayOfVariantOfDouble231(3) = 0.000000
arrayOfVariantOfDouble231(4) = 1.000000
arrayOfVariantOfDouble231(5) = 0.000000
arrayOfVariantOfDouble231(6) = 0.000000
arrayOfVariantOfDouble231(7) = 0.000000
arrayOfVariantOfDouble231(8) = 1.000000
arrayOfVariantOfDouble231(9) = -0.565712
arrayOfVariantOfDouble231(10) = 0.000000
arrayOfVariantOfDouble231(11) = 0.000000
move3.Apply arrayOfVariantOfDouble231

Set move3 = product5.Move

Set move3 = move3.MovableObject

Dim arrayOfVariantOfDouble232(11)
arrayOfVariantOfDouble232(0) = 1.000000
arrayOfVariantOfDouble232(1) = 0.000000
arrayOfVariantOfDouble232(2) = 0.000000
arrayOfVariantOfDouble232(3) = 0.000000
arrayOfVariantOfDouble232(4) = 1.000000
arrayOfVariantOfDouble232(5) = 0.000000
arrayOfVariantOfDouble232(6) = 0.000000
arrayOfVariantOfDouble232(7) = 0.000000
arrayOfVariantOfDouble232(8) = 1.000000
arrayOfVariantOfDouble232(9) = -0.745708
arrayOfVariantOfDouble232(10) = 0.000000
arrayOfVariantOfDouble232(11) = 0.000000
move3.Apply arrayOfVariantOfDouble232

Set move3 = product5.Move

Set move3 = move3.MovableObject

Dim arrayOfVariantOfDouble233(11)
arrayOfVariantOfDouble233(0) = 1.000000
arrayOfVariantOfDouble233(1) = 0.000000
arrayOfVariantOfDouble233(2) = 0.000000
arrayOfVariantOfDouble233(3) = 0.000000
arrayOfVariantOfDouble233(4) = 1.000000
arrayOfVariantOfDouble233(5) = 0.000000
arrayOfVariantOfDouble233(6) = 0.000000
arrayOfVariantOfDouble233(7) = 0.000000
arrayOfVariantOfDouble233(8) = 1.000000
arrayOfVariantOfDouble233(9) = -0.372860
arrayOfVariantOfDouble233(10) = 0.000000
arrayOfVariantOfDouble233(11) = 0.000000
move3.Apply arrayOfVariantOfDouble233

Set move3 = product5.Move

Set move3 = move3.MovableObject

Dim arrayOfVariantOfDouble234(11)
arrayOfVariantOfDouble234(0) = 1.000000
arrayOfVariantOfDouble234(1) = 0.000000
arrayOfVariantOfDouble234(2) = 0.000000
arrayOfVariantOfDouble234(3) = 0.000000
arrayOfVariantOfDouble234(4) = 1.000000
arrayOfVariantOfDouble234(5) = 0.000000
arrayOfVariantOfDouble234(6) = 0.000000
arrayOfVariantOfDouble234(7) = 0.000000
arrayOfVariantOfDouble234(8) = 1.000000
arrayOfVariantOfDouble234(9) = -0.565712
arrayOfVariantOfDouble234(10) = 0.000000
arrayOfVariantOfDouble234(11) = 0.000000
move3.Apply arrayOfVariantOfDouble234

Set move3 = product5.Move

Set move3 = move3.MovableObject

Dim arrayOfVariantOfDouble235(11)
arrayOfVariantOfDouble235(0) = 1.000000
arrayOfVariantOfDouble235(1) = 0.000000
arrayOfVariantOfDouble235(2) = 0.000000
arrayOfVariantOfDouble235(3) = 0.000000
arrayOfVariantOfDouble235(4) = 1.000000
arrayOfVariantOfDouble235(5) = 0.000000
arrayOfVariantOfDouble235(6) = 0.000000
arrayOfVariantOfDouble235(7) = 0.000000
arrayOfVariantOfDouble235(8) = 1.000000
arrayOfVariantOfDouble235(9) = -0.552851
arrayOfVariantOfDouble235(10) = 0.000000
arrayOfVariantOfDouble235(11) = 0.000000
move3.Apply arrayOfVariantOfDouble235

Set move3 = product5.Move

Set move3 = move3.MovableObject

Dim arrayOfVariantOfDouble236(11)
arrayOfVariantOfDouble236(0) = 1.000000
arrayOfVariantOfDouble236(1) = 0.000000
arrayOfVariantOfDouble236(2) = 0.000000
arrayOfVariantOfDouble236(3) = 0.000000
arrayOfVariantOfDouble236(4) = 1.000000
arrayOfVariantOfDouble236(5) = 0.000000
arrayOfVariantOfDouble236(6) = 0.000000
arrayOfVariantOfDouble236(7) = 0.000000
arrayOfVariantOfDouble236(8) = 1.000000
arrayOfVariantOfDouble236(9) = -0.372855
arrayOfVariantOfDouble236(10) = 0.000000
arrayOfVariantOfDouble236(11) = 0.000000
move3.Apply arrayOfVariantOfDouble236

Set move3 = product5.Move

Set move3 = move3.MovableObject

Dim arrayOfVariantOfDouble237(11)
arrayOfVariantOfDouble237(0) = 1.000000
arrayOfVariantOfDouble237(1) = 0.000000
arrayOfVariantOfDouble237(2) = 0.000000
arrayOfVariantOfDouble237(3) = 0.000000
arrayOfVariantOfDouble237(4) = 1.000000
arrayOfVariantOfDouble237(5) = 0.000000
arrayOfVariantOfDouble237(6) = 0.000000
arrayOfVariantOfDouble237(7) = 0.000000
arrayOfVariantOfDouble237(8) = 1.000000
arrayOfVariantOfDouble237(9) = -0.565714
arrayOfVariantOfDouble237(10) = 0.000000
arrayOfVariantOfDouble237(11) = 0.000000
move3.Apply arrayOfVariantOfDouble237

Set move3 = product5.Move

Set move3 = move3.MovableObject

Dim arrayOfVariantOfDouble238(11)
arrayOfVariantOfDouble238(0) = 1.000000
arrayOfVariantOfDouble238(1) = 0.000000
arrayOfVariantOfDouble238(2) = 0.000000
arrayOfVariantOfDouble238(3) = 0.000000
arrayOfVariantOfDouble238(4) = 1.000000
arrayOfVariantOfDouble238(5) = 0.000000
arrayOfVariantOfDouble238(6) = 0.000000
arrayOfVariantOfDouble238(7) = 0.000000
arrayOfVariantOfDouble238(8) = 1.000000
arrayOfVariantOfDouble238(9) = -0.372856
arrayOfVariantOfDouble238(10) = 0.000000
arrayOfVariantOfDouble238(11) = 0.000000
move3.Apply arrayOfVariantOfDouble238

Set move3 = product5.Move

Set move3 = move3.MovableObject

Dim arrayOfVariantOfDouble239(11)
arrayOfVariantOfDouble239(0) = 1.000000
arrayOfVariantOfDouble239(1) = 0.000000
arrayOfVariantOfDouble239(2) = 0.000000
arrayOfVariantOfDouble239(3) = 0.000000
arrayOfVariantOfDouble239(4) = 1.000000
arrayOfVariantOfDouble239(5) = 0.000000
arrayOfVariantOfDouble239(6) = 0.000000
arrayOfVariantOfDouble239(7) = 0.000000
arrayOfVariantOfDouble239(8) = 1.000000
arrayOfVariantOfDouble239(9) = -0.372855
arrayOfVariantOfDouble239(10) = 0.000000
arrayOfVariantOfDouble239(11) = 0.000000
move3.Apply arrayOfVariantOfDouble239

Set move3 = product5.Move

Set move3 = move3.MovableObject

Dim arrayOfVariantOfDouble240(11)
arrayOfVariantOfDouble240(0) = 1.000000
arrayOfVariantOfDouble240(1) = 0.000000
arrayOfVariantOfDouble240(2) = 0.000000
arrayOfVariantOfDouble240(3) = 0.000000
arrayOfVariantOfDouble240(4) = 1.000000
arrayOfVariantOfDouble240(5) = 0.000000
arrayOfVariantOfDouble240(6) = 0.000000
arrayOfVariantOfDouble240(7) = 0.000000
arrayOfVariantOfDouble240(8) = 1.000000
arrayOfVariantOfDouble240(9) = -0.745709
arrayOfVariantOfDouble240(10) = 0.000000
arrayOfVariantOfDouble240(11) = 0.000000
move3.Apply arrayOfVariantOfDouble240

Set move3 = product5.Move

Set move3 = move3.MovableObject

Dim arrayOfVariantOfDouble241(11)
arrayOfVariantOfDouble241(0) = 1.000000
arrayOfVariantOfDouble241(1) = 0.000000
arrayOfVariantOfDouble241(2) = 0.000000
arrayOfVariantOfDouble241(3) = 0.000000
arrayOfVariantOfDouble241(4) = 1.000000
arrayOfVariantOfDouble241(5) = 0.000000
arrayOfVariantOfDouble241(6) = 0.000000
arrayOfVariantOfDouble241(7) = 0.000000
arrayOfVariantOfDouble241(8) = 1.000000
arrayOfVariantOfDouble241(9) = -0.372859
arrayOfVariantOfDouble241(10) = 0.000000
arrayOfVariantOfDouble241(11) = 0.000000
move3.Apply arrayOfVariantOfDouble241

Set move3 = product5.Move

Set move3 = move3.MovableObject

Dim arrayOfVariantOfDouble242(11)
arrayOfVariantOfDouble242(0) = 1.000000
arrayOfVariantOfDouble242(1) = 0.000000
arrayOfVariantOfDouble242(2) = 0.000000
arrayOfVariantOfDouble242(3) = 0.000000
arrayOfVariantOfDouble242(4) = 1.000000
arrayOfVariantOfDouble242(5) = 0.000000
arrayOfVariantOfDouble242(6) = 0.000000
arrayOfVariantOfDouble242(7) = 0.000000
arrayOfVariantOfDouble242(8) = 1.000000
arrayOfVariantOfDouble242(9) = -0.372854
arrayOfVariantOfDouble242(10) = 0.000000
arrayOfVariantOfDouble242(11) = 0.000000
move3.Apply arrayOfVariantOfDouble242

Set move3 = product5.Move

Set move3 = move3.MovableObject

Dim arrayOfVariantOfDouble243(11)
arrayOfVariantOfDouble243(0) = 1.000000
arrayOfVariantOfDouble243(1) = 0.000000
arrayOfVariantOfDouble243(2) = 0.000000
arrayOfVariantOfDouble243(3) = 0.000000
arrayOfVariantOfDouble243(4) = 1.000000
arrayOfVariantOfDouble243(5) = 0.000000
arrayOfVariantOfDouble243(6) = 0.000000
arrayOfVariantOfDouble243(7) = 0.000000
arrayOfVariantOfDouble243(8) = 1.000000
arrayOfVariantOfDouble243(9) = -0.372856
arrayOfVariantOfDouble243(10) = 0.000000
arrayOfVariantOfDouble243(11) = 0.000000
move3.Apply arrayOfVariantOfDouble243

Set move3 = product5.Move

Set move3 = move3.MovableObject

Dim arrayOfVariantOfDouble244(11)
arrayOfVariantOfDouble244(0) = 1.000000
arrayOfVariantOfDouble244(1) = 0.000000
arrayOfVariantOfDouble244(2) = 0.000000
arrayOfVariantOfDouble244(3) = 0.000000
arrayOfVariantOfDouble244(4) = 1.000000
arrayOfVariantOfDouble244(5) = 0.000000
arrayOfVariantOfDouble244(6) = 0.000000
arrayOfVariantOfDouble244(7) = 0.000000
arrayOfVariantOfDouble244(8) = 1.000000
arrayOfVariantOfDouble244(9) = -0.565711
arrayOfVariantOfDouble244(10) = 0.000000
arrayOfVariantOfDouble244(11) = 0.000000
move3.Apply arrayOfVariantOfDouble244

Set move3 = product5.Move

Set move3 = move3.MovableObject

Dim arrayOfVariantOfDouble245(11)
arrayOfVariantOfDouble245(0) = 1.000000
arrayOfVariantOfDouble245(1) = 0.000000
arrayOfVariantOfDouble245(2) = 0.000000
arrayOfVariantOfDouble245(3) = 0.000000
arrayOfVariantOfDouble245(4) = 1.000000
arrayOfVariantOfDouble245(5) = 0.000000
arrayOfVariantOfDouble245(6) = 0.000000
arrayOfVariantOfDouble245(7) = 0.000000
arrayOfVariantOfDouble245(8) = 1.000000
arrayOfVariantOfDouble245(9) = -0.552850
arrayOfVariantOfDouble245(10) = 0.000000
arrayOfVariantOfDouble245(11) = 0.000000
move3.Apply arrayOfVariantOfDouble245

Set move3 = product5.Move

Set move3 = move3.MovableObject

Dim arrayOfVariantOfDouble246(11)
arrayOfVariantOfDouble246(0) = 1.000000
arrayOfVariantOfDouble246(1) = 0.000000
arrayOfVariantOfDouble246(2) = 0.000000
arrayOfVariantOfDouble246(3) = 0.000000
arrayOfVariantOfDouble246(4) = 1.000000
arrayOfVariantOfDouble246(5) = 0.000000
arrayOfVariantOfDouble246(6) = 0.000000
arrayOfVariantOfDouble246(7) = 0.000000
arrayOfVariantOfDouble246(8) = 1.000000
arrayOfVariantOfDouble246(9) = -0.565719
arrayOfVariantOfDouble246(10) = 0.000000
arrayOfVariantOfDouble246(11) = 0.000000
move3.Apply arrayOfVariantOfDouble246

Set move3 = product5.Move

Set move3 = move3.MovableObject

Dim arrayOfVariantOfDouble247(11)
arrayOfVariantOfDouble247(0) = 1.000000
arrayOfVariantOfDouble247(1) = 0.000000
arrayOfVariantOfDouble247(2) = 0.000000
arrayOfVariantOfDouble247(3) = 0.000000
arrayOfVariantOfDouble247(4) = 1.000000
arrayOfVariantOfDouble247(5) = 0.000000
arrayOfVariantOfDouble247(6) = 0.000000
arrayOfVariantOfDouble247(7) = 0.000000
arrayOfVariantOfDouble247(8) = 1.000000
arrayOfVariantOfDouble247(9) = -0.552850
arrayOfVariantOfDouble247(10) = 0.000000
arrayOfVariantOfDouble247(11) = 0.000000
move3.Apply arrayOfVariantOfDouble247

Set move3 = product5.Move

Set move3 = move3.MovableObject

Dim arrayOfVariantOfDouble248(11)
arrayOfVariantOfDouble248(0) = 1.000000
arrayOfVariantOfDouble248(1) = 0.000000
arrayOfVariantOfDouble248(2) = 0.000000
arrayOfVariantOfDouble248(3) = 0.000000
arrayOfVariantOfDouble248(4) = 1.000000
arrayOfVariantOfDouble248(5) = 0.000000
arrayOfVariantOfDouble248(6) = 0.000000
arrayOfVariantOfDouble248(7) = 0.000000
arrayOfVariantOfDouble248(8) = 1.000000
arrayOfVariantOfDouble248(9) = -0.565711
arrayOfVariantOfDouble248(10) = 0.000000
arrayOfVariantOfDouble248(11) = 0.000000
move3.Apply arrayOfVariantOfDouble248

Set move3 = product5.Move

Set move3 = move3.MovableObject

Dim arrayOfVariantOfDouble249(11)
arrayOfVariantOfDouble249(0) = 1.000000
arrayOfVariantOfDouble249(1) = 0.000000
arrayOfVariantOfDouble249(2) = 0.000000
arrayOfVariantOfDouble249(3) = 0.000000
arrayOfVariantOfDouble249(4) = 1.000000
arrayOfVariantOfDouble249(5) = 0.000000
arrayOfVariantOfDouble249(6) = 0.000000
arrayOfVariantOfDouble249(7) = 0.000000
arrayOfVariantOfDouble249(8) = 1.000000
arrayOfVariantOfDouble249(9) = -1.118568
arrayOfVariantOfDouble249(10) = 0.000000
arrayOfVariantOfDouble249(11) = 0.000000
move3.Apply arrayOfVariantOfDouble249

Set move3 = product5.Move

Set move3 = move3.MovableObject

Dim arrayOfVariantOfDouble250(11)
arrayOfVariantOfDouble250(0) = 1.000000
arrayOfVariantOfDouble250(1) = 0.000000
arrayOfVariantOfDouble250(2) = 0.000000
arrayOfVariantOfDouble250(3) = 0.000000
arrayOfVariantOfDouble250(4) = 1.000000
arrayOfVariantOfDouble250(5) = 0.000000
arrayOfVariantOfDouble250(6) = 0.000000
arrayOfVariantOfDouble250(7) = 0.000000
arrayOfVariantOfDouble250(8) = 1.000000
arrayOfVariantOfDouble250(9) = -0.372858
arrayOfVariantOfDouble250(10) = 0.000000
arrayOfVariantOfDouble250(11) = 0.000000
move3.Apply arrayOfVariantOfDouble250

Set move3 = product5.Move

Set move3 = move3.MovableObject

Dim arrayOfVariantOfDouble251(11)
arrayOfVariantOfDouble251(0) = 1.000000
arrayOfVariantOfDouble251(1) = 0.000000
arrayOfVariantOfDouble251(2) = 0.000000
arrayOfVariantOfDouble251(3) = 0.000000
arrayOfVariantOfDouble251(4) = 1.000000
arrayOfVariantOfDouble251(5) = 0.000000
arrayOfVariantOfDouble251(6) = 0.000000
arrayOfVariantOfDouble251(7) = 0.000000
arrayOfVariantOfDouble251(8) = 1.000000
arrayOfVariantOfDouble251(9) = -0.745713
arrayOfVariantOfDouble251(10) = 0.000000
arrayOfVariantOfDouble251(11) = 0.000000
move3.Apply arrayOfVariantOfDouble251

Set move3 = product5.Move

Set move3 = move3.MovableObject

Dim arrayOfVariantOfDouble252(11)
arrayOfVariantOfDouble252(0) = 1.000000
arrayOfVariantOfDouble252(1) = 0.000000
arrayOfVariantOfDouble252(2) = 0.000000
arrayOfVariantOfDouble252(3) = 0.000000
arrayOfVariantOfDouble252(4) = 1.000000
arrayOfVariantOfDouble252(5) = 0.000000
arrayOfVariantOfDouble252(6) = 0.000000
arrayOfVariantOfDouble252(7) = 0.000000
arrayOfVariantOfDouble252(8) = 1.000000
arrayOfVariantOfDouble252(9) = -0.938560
arrayOfVariantOfDouble252(10) = 0.000000
arrayOfVariantOfDouble252(11) = 0.000000
move3.Apply arrayOfVariantOfDouble252

Set move3 = product5.Move

Set move3 = move3.MovableObject

Dim arrayOfVariantOfDouble253(11)
arrayOfVariantOfDouble253(0) = 1.000000
arrayOfVariantOfDouble253(1) = 0.000000
arrayOfVariantOfDouble253(2) = 0.000000
arrayOfVariantOfDouble253(3) = 0.000000
arrayOfVariantOfDouble253(4) = 1.000000
arrayOfVariantOfDouble253(5) = 0.000000
arrayOfVariantOfDouble253(6) = 0.000000
arrayOfVariantOfDouble253(7) = 0.000000
arrayOfVariantOfDouble253(8) = 1.000000
arrayOfVariantOfDouble253(9) = -0.745716
arrayOfVariantOfDouble253(10) = 0.000000
arrayOfVariantOfDouble253(11) = 0.000000
move3.Apply arrayOfVariantOfDouble253

Set move3 = product5.Move

Set move3 = move3.MovableObject

Dim arrayOfVariantOfDouble254(11)
arrayOfVariantOfDouble254(0) = 1.000000
arrayOfVariantOfDouble254(1) = 0.000000
arrayOfVariantOfDouble254(2) = 0.000000
arrayOfVariantOfDouble254(3) = 0.000000
arrayOfVariantOfDouble254(4) = 1.000000
arrayOfVariantOfDouble254(5) = 0.000000
arrayOfVariantOfDouble254(6) = 0.000000
arrayOfVariantOfDouble254(7) = 0.000000
arrayOfVariantOfDouble254(8) = 1.000000
arrayOfVariantOfDouble254(9) = -0.565712
arrayOfVariantOfDouble254(10) = 0.000000
arrayOfVariantOfDouble254(11) = 0.000000
move3.Apply arrayOfVariantOfDouble254

Set move3 = product5.Move

Set move3 = move3.MovableObject

Dim arrayOfVariantOfDouble255(11)
arrayOfVariantOfDouble255(0) = 1.000000
arrayOfVariantOfDouble255(1) = 0.000000
arrayOfVariantOfDouble255(2) = 0.000000
arrayOfVariantOfDouble255(3) = 0.000000
arrayOfVariantOfDouble255(4) = 1.000000
arrayOfVariantOfDouble255(5) = 0.000000
arrayOfVariantOfDouble255(6) = 0.000000
arrayOfVariantOfDouble255(7) = 0.000000
arrayOfVariantOfDouble255(8) = 1.000000
arrayOfVariantOfDouble255(9) = -1.118561
arrayOfVariantOfDouble255(10) = 0.000000
arrayOfVariantOfDouble255(11) = 0.000000
move3.Apply arrayOfVariantOfDouble255

Set move3 = product5.Move

Set move3 = move3.MovableObject

Dim arrayOfVariantOfDouble256(11)
arrayOfVariantOfDouble256(0) = 1.000000
arrayOfVariantOfDouble256(1) = 0.000000
arrayOfVariantOfDouble256(2) = 0.000000
arrayOfVariantOfDouble256(3) = 0.000000
arrayOfVariantOfDouble256(4) = 1.000000
arrayOfVariantOfDouble256(5) = 0.000000
arrayOfVariantOfDouble256(6) = 0.000000
arrayOfVariantOfDouble256(7) = 0.000000
arrayOfVariantOfDouble256(8) = 1.000000
arrayOfVariantOfDouble256(9) = -0.372861
arrayOfVariantOfDouble256(10) = 0.000000
arrayOfVariantOfDouble256(11) = 0.000000
move3.Apply arrayOfVariantOfDouble256

Set move3 = product5.Move

Set move3 = move3.MovableObject

Dim arrayOfVariantOfDouble257(11)
arrayOfVariantOfDouble257(0) = 1.000000
arrayOfVariantOfDouble257(1) = 0.000000
arrayOfVariantOfDouble257(2) = 0.000000
arrayOfVariantOfDouble257(3) = 0.000000
arrayOfVariantOfDouble257(4) = 1.000000
arrayOfVariantOfDouble257(5) = 0.000000
arrayOfVariantOfDouble257(6) = 0.000000
arrayOfVariantOfDouble257(7) = 0.000000
arrayOfVariantOfDouble257(8) = 1.000000
arrayOfVariantOfDouble257(9) = -0.372856
arrayOfVariantOfDouble257(10) = 0.000000
arrayOfVariantOfDouble257(11) = 0.000000
move3.Apply arrayOfVariantOfDouble257

Set move3 = product5.Move

Set move3 = move3.MovableObject

Dim arrayOfVariantOfDouble258(11)
arrayOfVariantOfDouble258(0) = 1.000000
arrayOfVariantOfDouble258(1) = 0.000000
arrayOfVariantOfDouble258(2) = 0.000000
arrayOfVariantOfDouble258(3) = 0.000000
arrayOfVariantOfDouble258(4) = 1.000000
arrayOfVariantOfDouble258(5) = 0.000000
arrayOfVariantOfDouble258(6) = 0.000000
arrayOfVariantOfDouble258(7) = 0.000000
arrayOfVariantOfDouble258(8) = 1.000000
arrayOfVariantOfDouble258(9) = -1.118560
arrayOfVariantOfDouble258(10) = 0.000000
arrayOfVariantOfDouble258(11) = 0.000000
move3.Apply arrayOfVariantOfDouble258

Set move3 = product5.Move

Set move3 = move3.MovableObject

Dim arrayOfVariantOfDouble259(11)
arrayOfVariantOfDouble259(0) = 1.000000
arrayOfVariantOfDouble259(1) = 0.000000
arrayOfVariantOfDouble259(2) = 0.000000
arrayOfVariantOfDouble259(3) = 0.000000
arrayOfVariantOfDouble259(4) = 1.000000
arrayOfVariantOfDouble259(5) = 0.000000
arrayOfVariantOfDouble259(6) = 0.000000
arrayOfVariantOfDouble259(7) = 0.000000
arrayOfVariantOfDouble259(8) = 1.000000
arrayOfVariantOfDouble259(9) = -0.192863
arrayOfVariantOfDouble259(10) = 0.000000
arrayOfVariantOfDouble259(11) = 0.000000
move3.Apply arrayOfVariantOfDouble259

Set move3 = product5.Move

Set move3 = move3.MovableObject

Dim arrayOfVariantOfDouble260(11)
arrayOfVariantOfDouble260(0) = 1.000000
arrayOfVariantOfDouble260(1) = 0.000000
arrayOfVariantOfDouble260(2) = 0.000000
arrayOfVariantOfDouble260(3) = 0.000000
arrayOfVariantOfDouble260(4) = 1.000000
arrayOfVariantOfDouble260(5) = 0.000000
arrayOfVariantOfDouble260(6) = 0.000000
arrayOfVariantOfDouble260(7) = 0.000000
arrayOfVariantOfDouble260(8) = 1.000000
arrayOfVariantOfDouble260(9) = -0.372849
arrayOfVariantOfDouble260(10) = 0.000000
arrayOfVariantOfDouble260(11) = 0.000000
move3.Apply arrayOfVariantOfDouble260

Set move3 = product5.Move

Set move3 = move3.MovableObject

Dim arrayOfVariantOfDouble261(11)
arrayOfVariantOfDouble261(0) = 1.000000
arrayOfVariantOfDouble261(1) = 0.000000
arrayOfVariantOfDouble261(2) = 0.000000
arrayOfVariantOfDouble261(3) = 0.000000
arrayOfVariantOfDouble261(4) = 1.000000
arrayOfVariantOfDouble261(5) = 0.000000
arrayOfVariantOfDouble261(6) = 0.000000
arrayOfVariantOfDouble261(7) = 0.000000
arrayOfVariantOfDouble261(8) = 1.000000
arrayOfVariantOfDouble261(9) = -0.745715
arrayOfVariantOfDouble261(10) = 0.000000
arrayOfVariantOfDouble261(11) = 0.000000
move3.Apply arrayOfVariantOfDouble261

Set move3 = product5.Move

Set move3 = move3.MovableObject

Dim arrayOfVariantOfDouble262(11)
arrayOfVariantOfDouble262(0) = 1.000000
arrayOfVariantOfDouble262(1) = 0.000000
arrayOfVariantOfDouble262(2) = 0.000000
arrayOfVariantOfDouble262(3) = 0.000000
arrayOfVariantOfDouble262(4) = 1.000000
arrayOfVariantOfDouble262(5) = 0.000000
arrayOfVariantOfDouble262(6) = 0.000000
arrayOfVariantOfDouble262(7) = 0.000000
arrayOfVariantOfDouble262(8) = 1.000000
arrayOfVariantOfDouble262(9) = -0.745710
arrayOfVariantOfDouble262(10) = 0.000000
arrayOfVariantOfDouble262(11) = 0.000000
move3.Apply arrayOfVariantOfDouble262

Set move3 = product5.Move

Set move3 = move3.MovableObject

Dim arrayOfVariantOfDouble263(11)
arrayOfVariantOfDouble263(0) = 1.000000
arrayOfVariantOfDouble263(1) = 0.000000
arrayOfVariantOfDouble263(2) = 0.000000
arrayOfVariantOfDouble263(3) = 0.000000
arrayOfVariantOfDouble263(4) = 1.000000
arrayOfVariantOfDouble263(5) = 0.000000
arrayOfVariantOfDouble263(6) = 0.000000
arrayOfVariantOfDouble263(7) = 0.000000
arrayOfVariantOfDouble263(8) = 1.000000
arrayOfVariantOfDouble263(9) = -0.565711
arrayOfVariantOfDouble263(10) = 0.000000
arrayOfVariantOfDouble263(11) = 0.000000
move3.Apply arrayOfVariantOfDouble263

Set move3 = product5.Move

Set move3 = move3.MovableObject

Dim arrayOfVariantOfDouble264(11)
arrayOfVariantOfDouble264(0) = 1.000000
arrayOfVariantOfDouble264(1) = 0.000000
arrayOfVariantOfDouble264(2) = 0.000000
arrayOfVariantOfDouble264(3) = 0.000000
arrayOfVariantOfDouble264(4) = 1.000000
arrayOfVariantOfDouble264(5) = 0.000000
arrayOfVariantOfDouble264(6) = 0.000000
arrayOfVariantOfDouble264(7) = 0.000000
arrayOfVariantOfDouble264(8) = 1.000000
arrayOfVariantOfDouble264(9) = -0.372853
arrayOfVariantOfDouble264(10) = 0.000000
arrayOfVariantOfDouble264(11) = 0.000000
move3.Apply arrayOfVariantOfDouble264

Set move3 = product5.Move

Set move3 = move3.MovableObject

Dim arrayOfVariantOfDouble265(11)
arrayOfVariantOfDouble265(0) = 1.000000
arrayOfVariantOfDouble265(1) = 0.000000
arrayOfVariantOfDouble265(2) = 0.000000
arrayOfVariantOfDouble265(3) = 0.000000
arrayOfVariantOfDouble265(4) = 1.000000
arrayOfVariantOfDouble265(5) = 0.000000
arrayOfVariantOfDouble265(6) = 0.000000
arrayOfVariantOfDouble265(7) = 0.000000
arrayOfVariantOfDouble265(8) = 1.000000
arrayOfVariantOfDouble265(9) = -0.372857
arrayOfVariantOfDouble265(10) = 0.000000
arrayOfVariantOfDouble265(11) = 0.000000
move3.Apply arrayOfVariantOfDouble265

Set move3 = product5.Move

Set move3 = move3.MovableObject

Dim arrayOfVariantOfDouble266(11)
arrayOfVariantOfDouble266(0) = 1.000000
arrayOfVariantOfDouble266(1) = 0.000000
arrayOfVariantOfDouble266(2) = 0.000000
arrayOfVariantOfDouble266(3) = 0.000000
arrayOfVariantOfDouble266(4) = 1.000000
arrayOfVariantOfDouble266(5) = 0.000000
arrayOfVariantOfDouble266(6) = 0.000000
arrayOfVariantOfDouble266(7) = 0.000000
arrayOfVariantOfDouble266(8) = 1.000000
arrayOfVariantOfDouble266(9) = -0.372856
arrayOfVariantOfDouble266(10) = 0.000000
arrayOfVariantOfDouble266(11) = 0.000000
move3.Apply arrayOfVariantOfDouble266

Set move3 = product5.Move

Set move3 = move3.MovableObject

Dim arrayOfVariantOfDouble267(11)
arrayOfVariantOfDouble267(0) = 1.000000
arrayOfVariantOfDouble267(1) = 0.000000
arrayOfVariantOfDouble267(2) = 0.000000
arrayOfVariantOfDouble267(3) = 0.000000
arrayOfVariantOfDouble267(4) = 1.000000
arrayOfVariantOfDouble267(5) = 0.000000
arrayOfVariantOfDouble267(6) = 0.000000
arrayOfVariantOfDouble267(7) = 0.000000
arrayOfVariantOfDouble267(8) = 1.000000
arrayOfVariantOfDouble267(9) = -0.565716
arrayOfVariantOfDouble267(10) = 0.000000
arrayOfVariantOfDouble267(11) = 0.000000
move3.Apply arrayOfVariantOfDouble267

Set move3 = product5.Move

Set move3 = move3.MovableObject

Dim arrayOfVariantOfDouble268(11)
arrayOfVariantOfDouble268(0) = 1.000000
arrayOfVariantOfDouble268(1) = 0.000000
arrayOfVariantOfDouble268(2) = 0.000000
arrayOfVariantOfDouble268(3) = 0.000000
arrayOfVariantOfDouble268(4) = 1.000000
arrayOfVariantOfDouble268(5) = 0.000000
arrayOfVariantOfDouble268(6) = 0.000000
arrayOfVariantOfDouble268(7) = 0.000000
arrayOfVariantOfDouble268(8) = 1.000000
arrayOfVariantOfDouble268(9) = -0.372850
arrayOfVariantOfDouble268(10) = 0.000000
arrayOfVariantOfDouble268(11) = 0.000000
move3.Apply arrayOfVariantOfDouble268

Set move3 = product5.Move

Set move3 = move3.MovableObject

Dim arrayOfVariantOfDouble269(11)
arrayOfVariantOfDouble269(0) = 1.000000
arrayOfVariantOfDouble269(1) = 0.000000
arrayOfVariantOfDouble269(2) = 0.000000
arrayOfVariantOfDouble269(3) = 0.000000
arrayOfVariantOfDouble269(4) = 1.000000
arrayOfVariantOfDouble269(5) = 0.000000
arrayOfVariantOfDouble269(6) = 0.000000
arrayOfVariantOfDouble269(7) = 0.000000
arrayOfVariantOfDouble269(8) = 1.000000
arrayOfVariantOfDouble269(9) = -0.180000
arrayOfVariantOfDouble269(10) = 0.000000
arrayOfVariantOfDouble269(11) = 0.000000
move3.Apply arrayOfVariantOfDouble269

Set move3 = product5.Move

Set move3 = move3.MovableObject

Dim arrayOfVariantOfDouble270(11)
arrayOfVariantOfDouble270(0) = 1.000000
arrayOfVariantOfDouble270(1) = 0.000000
arrayOfVariantOfDouble270(2) = 0.000000
arrayOfVariantOfDouble270(3) = 0.000000
arrayOfVariantOfDouble270(4) = 1.000000
arrayOfVariantOfDouble270(5) = 0.000000
arrayOfVariantOfDouble270(6) = 0.000000
arrayOfVariantOfDouble270(7) = 0.000000
arrayOfVariantOfDouble270(8) = 1.000000
arrayOfVariantOfDouble270(9) = -0.385713
arrayOfVariantOfDouble270(10) = 0.000000
arrayOfVariantOfDouble270(11) = 0.000000
move3.Apply arrayOfVariantOfDouble270

Set move3 = product5.Move

Set move3 = move3.MovableObject

Dim arrayOfVariantOfDouble271(11)
arrayOfVariantOfDouble271(0) = 1.000000
arrayOfVariantOfDouble271(1) = 0.000000
arrayOfVariantOfDouble271(2) = 0.000000
arrayOfVariantOfDouble271(3) = 0.000000
arrayOfVariantOfDouble271(4) = 1.000000
arrayOfVariantOfDouble271(5) = 0.000000
arrayOfVariantOfDouble271(6) = 0.000000
arrayOfVariantOfDouble271(7) = 0.000000
arrayOfVariantOfDouble271(8) = 1.000000
arrayOfVariantOfDouble271(9) = -0.179996
arrayOfVariantOfDouble271(10) = 0.000000
arrayOfVariantOfDouble271(11) = 0.000000
move3.Apply arrayOfVariantOfDouble271

Set move3 = product5.Move

Set move3 = move3.MovableObject

Dim arrayOfVariantOfDouble272(11)
arrayOfVariantOfDouble272(0) = 1.000000
arrayOfVariantOfDouble272(1) = 0.000000
arrayOfVariantOfDouble272(2) = 0.000000
arrayOfVariantOfDouble272(3) = 0.000000
arrayOfVariantOfDouble272(4) = 1.000000
arrayOfVariantOfDouble272(5) = 0.000000
arrayOfVariantOfDouble272(6) = 0.000000
arrayOfVariantOfDouble272(7) = 0.000000
arrayOfVariantOfDouble272(8) = 1.000000
arrayOfVariantOfDouble272(9) = -0.192861
arrayOfVariantOfDouble272(10) = 0.000000
arrayOfVariantOfDouble272(11) = 0.000000
move3.Apply arrayOfVariantOfDouble272

Set move3 = product5.Move

Set move3 = move3.MovableObject

Dim arrayOfVariantOfDouble273(11)
arrayOfVariantOfDouble273(0) = 1.000000
arrayOfVariantOfDouble273(1) = 0.000000
arrayOfVariantOfDouble273(2) = 0.000000
arrayOfVariantOfDouble273(3) = 0.000000
arrayOfVariantOfDouble273(4) = 1.000000
arrayOfVariantOfDouble273(5) = 0.000000
arrayOfVariantOfDouble273(6) = 0.000000
arrayOfVariantOfDouble273(7) = 0.000000
arrayOfVariantOfDouble273(8) = 1.000000
arrayOfVariantOfDouble273(9) = -0.179996
arrayOfVariantOfDouble273(10) = 0.000000
arrayOfVariantOfDouble273(11) = 0.000000
move3.Apply arrayOfVariantOfDouble273

Set move3 = product5.Move

Set move3 = move3.MovableObject

Dim arrayOfVariantOfDouble274(11)
arrayOfVariantOfDouble274(0) = 1.000000
arrayOfVariantOfDouble274(1) = 0.000000
arrayOfVariantOfDouble274(2) = 0.000000
arrayOfVariantOfDouble274(3) = 0.000000
arrayOfVariantOfDouble274(4) = 1.000000
arrayOfVariantOfDouble274(5) = 0.000000
arrayOfVariantOfDouble274(6) = 0.000000
arrayOfVariantOfDouble274(7) = 0.000000
arrayOfVariantOfDouble274(8) = 1.000000
arrayOfVariantOfDouble274(9) = -0.192861
arrayOfVariantOfDouble274(10) = 0.000000
arrayOfVariantOfDouble274(11) = 0.000000
move3.Apply arrayOfVariantOfDouble274

Set constraints1 = product1.Connections("CATIAConstraints")

Set reference15 = product1.CreateReferenceFromName("A2/DM.2/!Axis:(Selection_RSur:(Face:(Brp:(Pocket.2;0:(Brp:(Sketch.3;4)));None:();Cf11:());Pocket.2_ResultOUT;Z0;G4162))")

Dim reference33 As Reference
Set reference33 = product1.CreateReferenceFromName("A2/Bolt.1/!Axis:(Selection_RSur:(Face:(Brp:(Shaft.1;0:(Brp:(Sketch.1;10)));None:();Cf11:());Pad.1_ResultOUT;Z0;G4162))")

Dim constraint20 As Constraint
Set constraint20 = constraints1.AddBiEltCst(catCstTypeOn, reference15, reference33)

Set constraints1 = product1.Connections("CATIAConstraints")

Dim reference34 As Reference
Set reference34 = product1.CreateReferenceFromName("A2/DM.2/!Selection_RSur:(Face:(Brp:(Pad.1;0:(Brp:(Sketch.1;8)));None:();Cf11:());Pocket.2_ResultOUT;Z0;G4162)")

Dim reference35 As Reference
Set reference35 = product1.CreateReferenceFromName("A2/Bolt.1/!Selection_RSur:(Face:(Brp:(Shaft.1;0:(Brp:(Sketch.1;8)));None:();Cf11:());Pad.1_ResultOUT;Z0;G4162)")

Dim constraint21 As Constraint
Set constraint21 = constraints1.AddBiEltCst(catCstTypeSurfContact, reference34, reference35)

product1.Update 

Set constraints1 = product1.Connections("CATIAConstraints")

Dim reference36 As Reference
Set reference36 = product1.CreateReferenceFromName("A2/Bolt.1/!Selection_REdge:(Edge:(Face:(Brp:(Pad.1;0:(Brp:(Sketch.2;7)));None:();Cf11:());Face:(Brp:(Pad.1;2);None:();Cf11:());None:(Limits1:();Limits2:());Cf11:());Pad.1_ResultOUT;Z0;G4162)")

Dim reference37 As Reference
Set reference37 = product1.CreateReferenceFromName("A2/Plate.1/!Selection_REdge:(Edge:(Face:(Brp:(Pad.1;1);None:();Cf11:());Face:(Brp:(Pad.1;0:(Brp:(Sketch.1;9)));None:();Cf11:());None:(Limits1:();Limits2:());Cf11:());Pad.1_ResultOUT;Z0;G4162)")

Dim constraint22 As Constraint
Set constraint22 = constraints1.AddBiEltCst(catCstTypeAngle, reference36, reference37)

Dim angle3 As Dimension
Set angle3 = constraint22.Dimension

angle3.Value = 0.000000

Dim arrayOfVariantOfBSTR9(0)
arrayOfVariantOfBSTR9(0) = ".\SubAssembly\Bolt.CATPart"
products1.AddComponentsFromFiles arrayOfVariantOfBSTR9, "All"

Set constraints1 = product1.Connections("CATIAConstraints")

Set reference11 = product1.CreateReferenceFromName("A2/DM.2/!Axis:(Selection_RSur:(Face:(Brp:(Pocket.2;0:(Brp:(Sketch.3;8)));None:();Cf11:());Pocket.2_ResultOUT;Z0;G4162))")

Dim reference38 As Reference
Set reference38 = product1.CreateReferenceFromName("A2/Bolt.2/!Axis:(Selection_RSur:(Face:(Brp:(Shaft.1;0:(Brp:(Sketch.1;10)));None:();Cf11:());Pad.1_ResultOUT;Z0;G4162))")

Dim constraint23 As Constraint
Set constraint23 = constraints1.AddBiEltCst(catCstTypeOn, reference11, reference38)

Set constraints1 = product1.Connections("CATIAConstraints")

Set reference34 = product1.CreateReferenceFromName("A2/DM.2/!Selection_RSur:(Face:(Brp:(Pad.1;0:(Brp:(Sketch.1;8)));None:();Cf11:());Pocket.2_ResultOUT;Z0;G4162)")

Dim reference39 As Reference
Set reference39 = product1.CreateReferenceFromName("A2/Bolt.2/!Selection_RSur:(Face:(Brp:(Shaft.1;0:(Brp:(Sketch.1;8)));None:();Cf11:());Pad.1_ResultOUT;Z0;G4162)")

Dim constraint24 As Constraint
Set constraint24 = constraints1.AddBiEltCst(catCstTypeSurfContact, reference34, reference39)

product1.Update 

Set constraints1 = product1.Connections("CATIAConstraints")

Set reference37 = product1.CreateReferenceFromName("A2/Plate.1/!Selection_REdge:(Edge:(Face:(Brp:(Pad.1;1);None:();Cf11:());Face:(Brp:(Pad.1;0:(Brp:(Sketch.1;9)));None:();Cf11:());None:(Limits1:();Limits2:());Cf11:());Pad.1_ResultOUT;Z0;G4162)")

Dim reference40 As Reference
Set reference40 = product1.CreateReferenceFromName("A2/Bolt.2/!Selection_REdge:(Edge:(Face:(Brp:(Pad.1;0:(Brp:(Sketch.2;7)));None:();Cf11:());Face:(Brp:(Pad.1;2);None:();Cf11:());None:(Limits1:();Limits2:());Cf11:());Pad.1_ResultOUT;Z0;G4162)")

Dim constraint25 As Constraint
Set constraint25 = constraints1.AddBiEltCst(catCstTypeAngle, reference37, reference40)

Dim angle4 As Dimension
Set angle4 = constraint25.Dimension

angle4.Value = 0.000000

Dim arrayOfVariantOfBSTR10(0)
arrayOfVariantOfBSTR10(0) = ".\SubAssembly\Bolt.CATPart"
products1.AddComponentsFromFiles arrayOfVariantOfBSTR10, "All"

Set constraints1 = product1.Connections("CATIAConstraints")

Set reference13 = product1.CreateReferenceFromName("A2/DM.2/!Axis:(Selection_RSur:(Face:(Brp:(Pocket.2;0:(Brp:(Sketch.3;6)));None:();Cf11:());Pocket.2_ResultOUT;Z0;G4162))")

Dim reference41 As Reference
Set reference41 = product1.CreateReferenceFromName("A2/Bolt.3/!Axis:(Selection_RSur:(Face:(Brp:(Shaft.1;0:(Brp:(Sketch.1;10)));None:();Cf11:());Pad.1_ResultOUT;Z0;G4162))")

Dim constraint26 As Constraint
Set constraint26 = constraints1.AddBiEltCst(catCstTypeOn, reference13, reference41)

Set constraints1 = product1.Connections("CATIAConstraints")

Set reference34 = product1.CreateReferenceFromName("A2/DM.2/!Selection_RSur:(Face:(Brp:(Pad.1;0:(Brp:(Sketch.1;8)));None:();Cf11:());Pocket.2_ResultOUT;Z0;G4162)")

Dim reference42 As Reference
Set reference42 = product1.CreateReferenceFromName("A2/Bolt.3/!Selection_RSur:(Face:(Brp:(Shaft.1;0:(Brp:(Sketch.1;8)));None:();Cf11:());Pad.1_ResultOUT;Z0;G4162)")

Dim constraint27 As Constraint
Set constraint27 = constraints1.AddBiEltCst(catCstTypeSurfContact, reference34, reference42)

product1.Update 

Set constraints1 = product1.Connections("CATIAConstraints")

Dim reference43 As Reference
Set reference43 = product1.CreateReferenceFromName("A2/Bolt.3/!Selection_REdge:(Edge:(Face:(Brp:(Pad.1;0:(Brp:(Sketch.2;7)));None:();Cf11:());Face:(Brp:(Pad.1;2);None:();Cf11:());None:(Limits1:();Limits2:());Cf11:());Pad.1_ResultOUT;Z0;G4162)")

Set reference37 = product1.CreateReferenceFromName("A2/Plate.1/!Selection_REdge:(Edge:(Face:(Brp:(Pad.1;1);None:();Cf11:());Face:(Brp:(Pad.1;0:(Brp:(Sketch.1;9)));None:();Cf11:());None:(Limits1:();Limits2:());Cf11:());Pad.1_ResultOUT;Z0;G4162)")

Dim constraint28 As Constraint
Set constraint28 = constraints1.AddBiEltCst(catCstTypeAngle, reference43, reference37)

Dim angle5 As Dimension
Set angle5 = constraint28.Dimension

angle5.Value = 0.000000



Dim arrayOfVariantOfBSTR11(0)
arrayOfVariantOfBSTR11(0) = ".\SubAssembly\Bolt.CATPart"
products1.AddComponentsFromFiles arrayOfVariantOfBSTR11, "All"

Dim product6 As Product
Set product6 = products1.Item("Bolt.4")

Dim move4 As Move
Set move4 = product6.Move

Set move4 = move4.MovableObject

Dim arrayOfVariantOfDouble275(11)
arrayOfVariantOfDouble275(0) = 1.000000
arrayOfVariantOfDouble275(1) = 0.000000
arrayOfVariantOfDouble275(2) = 0.000000
arrayOfVariantOfDouble275(3) = 0.000000
arrayOfVariantOfDouble275(4) = 1.000000
arrayOfVariantOfDouble275(5) = 0.000000
arrayOfVariantOfDouble275(6) = 0.000000
arrayOfVariantOfDouble275(7) = 0.000000
arrayOfVariantOfDouble275(8) = 1.000000
arrayOfVariantOfDouble275(9) = 0.000000
arrayOfVariantOfDouble275(10) = 3.910226
arrayOfVariantOfDouble275(11) = 0.000000
move4.Apply arrayOfVariantOfDouble275

Set move4 = product6.Move

Set move4 = move4.MovableObject

Dim arrayOfVariantOfDouble276(11)
arrayOfVariantOfDouble276(0) = 1.000000
arrayOfVariantOfDouble276(1) = 0.000000
arrayOfVariantOfDouble276(2) = 0.000000
arrayOfVariantOfDouble276(3) = 0.000000
arrayOfVariantOfDouble276(4) = 1.000000
arrayOfVariantOfDouble276(5) = 0.000000
arrayOfVariantOfDouble276(6) = 0.000000
arrayOfVariantOfDouble276(7) = 0.000000
arrayOfVariantOfDouble276(8) = 1.000000
arrayOfVariantOfDouble276(9) = 0.000000
arrayOfVariantOfDouble276(10) = 1.712323
arrayOfVariantOfDouble276(11) = 0.000000
move4.Apply arrayOfVariantOfDouble276

Set move4 = product6.Move

Set move4 = move4.MovableObject

Dim arrayOfVariantOfDouble277(11)
arrayOfVariantOfDouble277(0) = 1.000000
arrayOfVariantOfDouble277(1) = 0.000000
arrayOfVariantOfDouble277(2) = 0.000000
arrayOfVariantOfDouble277(3) = 0.000000
arrayOfVariantOfDouble277(4) = 1.000000
arrayOfVariantOfDouble277(5) = 0.000000
arrayOfVariantOfDouble277(6) = 0.000000
arrayOfVariantOfDouble277(7) = 0.000000
arrayOfVariantOfDouble277(8) = 1.000000
arrayOfVariantOfDouble277(9) = 0.000000
arrayOfVariantOfDouble277(10) = 1.654377
arrayOfVariantOfDouble277(11) = 0.000000
move4.Apply arrayOfVariantOfDouble277

Set move4 = product6.Move

Set move4 = move4.MovableObject

Dim arrayOfVariantOfDouble278(11)
arrayOfVariantOfDouble278(0) = 1.000000
arrayOfVariantOfDouble278(1) = 0.000000
arrayOfVariantOfDouble278(2) = 0.000000
arrayOfVariantOfDouble278(3) = 0.000000
arrayOfVariantOfDouble278(4) = 1.000000
arrayOfVariantOfDouble278(5) = 0.000000
arrayOfVariantOfDouble278(6) = 0.000000
arrayOfVariantOfDouble278(7) = 0.000000
arrayOfVariantOfDouble278(8) = 1.000000
arrayOfVariantOfDouble278(9) = 0.000000
arrayOfVariantOfDouble278(10) = 2.452606
arrayOfVariantOfDouble278(11) = 0.000000
move4.Apply arrayOfVariantOfDouble278

Set move4 = product6.Move

Set move4 = move4.MovableObject

Dim arrayOfVariantOfDouble279(11)
arrayOfVariantOfDouble279(0) = 1.000000
arrayOfVariantOfDouble279(1) = 0.000000
arrayOfVariantOfDouble279(2) = 0.000000
arrayOfVariantOfDouble279(3) = 0.000000
arrayOfVariantOfDouble279(4) = 1.000000
arrayOfVariantOfDouble279(5) = 0.000000
arrayOfVariantOfDouble279(6) = 0.000000
arrayOfVariantOfDouble279(7) = 0.000000
arrayOfVariantOfDouble279(8) = 1.000000
arrayOfVariantOfDouble279(9) = 0.000000
arrayOfVariantOfDouble279(10) = 2.452599
arrayOfVariantOfDouble279(11) = 0.000000
move4.Apply arrayOfVariantOfDouble279

Set move4 = product6.Move

Set move4 = move4.MovableObject

Dim arrayOfVariantOfDouble280(11)
arrayOfVariantOfDouble280(0) = 1.000000
arrayOfVariantOfDouble280(1) = 0.000000
arrayOfVariantOfDouble280(2) = 0.000000
arrayOfVariantOfDouble280(3) = 0.000000
arrayOfVariantOfDouble280(4) = 1.000000
arrayOfVariantOfDouble280(5) = 0.000000
arrayOfVariantOfDouble280(6) = 0.000000
arrayOfVariantOfDouble280(7) = 0.000000
arrayOfVariantOfDouble280(8) = 1.000000
arrayOfVariantOfDouble280(9) = 0.000000
arrayOfVariantOfDouble280(10) = 1.654374
arrayOfVariantOfDouble280(11) = 0.000000
move4.Apply arrayOfVariantOfDouble280

Set move4 = product6.Move

Set move4 = move4.MovableObject

Dim arrayOfVariantOfDouble281(11)
arrayOfVariantOfDouble281(0) = 1.000000
arrayOfVariantOfDouble281(1) = 0.000000
arrayOfVariantOfDouble281(2) = 0.000000
arrayOfVariantOfDouble281(3) = 0.000000
arrayOfVariantOfDouble281(4) = 1.000000
arrayOfVariantOfDouble281(5) = 0.000000
arrayOfVariantOfDouble281(6) = 0.000000
arrayOfVariantOfDouble281(7) = 0.000000
arrayOfVariantOfDouble281(8) = 1.000000
arrayOfVariantOfDouble281(9) = 0.000000
arrayOfVariantOfDouble281(10) = 1.654378
arrayOfVariantOfDouble281(11) = 0.000000
move4.Apply arrayOfVariantOfDouble281

Set move4 = product6.Move

Set move4 = move4.MovableObject

Dim arrayOfVariantOfDouble282(11)
arrayOfVariantOfDouble282(0) = 1.000000
arrayOfVariantOfDouble282(1) = 0.000000
arrayOfVariantOfDouble282(2) = 0.000000
arrayOfVariantOfDouble282(3) = 0.000000
arrayOfVariantOfDouble282(4) = 1.000000
arrayOfVariantOfDouble282(5) = 0.000000
arrayOfVariantOfDouble282(6) = 0.000000
arrayOfVariantOfDouble282(7) = 0.000000
arrayOfVariantOfDouble282(8) = 1.000000
arrayOfVariantOfDouble282(9) = 0.000000
arrayOfVariantOfDouble282(10) = 1.654371
arrayOfVariantOfDouble282(11) = 0.000000
move4.Apply arrayOfVariantOfDouble282

Set move4 = product6.Move

Set move4 = move4.MovableObject

Dim arrayOfVariantOfDouble283(11)
arrayOfVariantOfDouble283(0) = 1.000000
arrayOfVariantOfDouble283(1) = 0.000000
arrayOfVariantOfDouble283(2) = 0.000000
arrayOfVariantOfDouble283(3) = 0.000000
arrayOfVariantOfDouble283(4) = 1.000000
arrayOfVariantOfDouble283(5) = 0.000000
arrayOfVariantOfDouble283(6) = 0.000000
arrayOfVariantOfDouble283(7) = 0.000000
arrayOfVariantOfDouble283(8) = 1.000000
arrayOfVariantOfDouble283(9) = 0.000000
arrayOfVariantOfDouble283(10) = 1.654385
arrayOfVariantOfDouble283(11) = 0.000000
move4.Apply arrayOfVariantOfDouble283

Set move4 = product6.Move

Set move4 = move4.MovableObject

Dim arrayOfVariantOfDouble284(11)
arrayOfVariantOfDouble284(0) = 1.000000
arrayOfVariantOfDouble284(1) = 0.000000
arrayOfVariantOfDouble284(2) = 0.000000
arrayOfVariantOfDouble284(3) = 0.000000
arrayOfVariantOfDouble284(4) = 1.000000
arrayOfVariantOfDouble284(5) = 0.000000
arrayOfVariantOfDouble284(6) = 0.000000
arrayOfVariantOfDouble284(7) = 0.000000
arrayOfVariantOfDouble284(8) = 1.000000
arrayOfVariantOfDouble284(9) = 0.000000
arrayOfVariantOfDouble284(10) = 2.452609
arrayOfVariantOfDouble284(11) = 0.000000
move4.Apply arrayOfVariantOfDouble284

Set move4 = product6.Move

Set move4 = move4.MovableObject

Dim arrayOfVariantOfDouble285(11)
arrayOfVariantOfDouble285(0) = 1.000000
arrayOfVariantOfDouble285(1) = 0.000000
arrayOfVariantOfDouble285(2) = 0.000000
arrayOfVariantOfDouble285(3) = 0.000000
arrayOfVariantOfDouble285(4) = 1.000000
arrayOfVariantOfDouble285(5) = 0.000000
arrayOfVariantOfDouble285(6) = 0.000000
arrayOfVariantOfDouble285(7) = 0.000000
arrayOfVariantOfDouble285(8) = 1.000000
arrayOfVariantOfDouble285(9) = 0.000000
arrayOfVariantOfDouble285(10) = 0.798214
arrayOfVariantOfDouble285(11) = 0.000000
move4.Apply arrayOfVariantOfDouble285

Set move4 = product6.Move

Set move4 = move4.MovableObject

Dim arrayOfVariantOfDouble286(11)
arrayOfVariantOfDouble286(0) = 1.000000
arrayOfVariantOfDouble286(1) = 0.000000
arrayOfVariantOfDouble286(2) = 0.000000
arrayOfVariantOfDouble286(3) = 0.000000
arrayOfVariantOfDouble286(4) = 1.000000
arrayOfVariantOfDouble286(5) = 0.000000
arrayOfVariantOfDouble286(6) = 0.000000
arrayOfVariantOfDouble286(7) = 0.000000
arrayOfVariantOfDouble286(8) = 1.000000
arrayOfVariantOfDouble286(9) = 0.000000
arrayOfVariantOfDouble286(10) = 1.654377
arrayOfVariantOfDouble286(11) = 0.000000
move4.Apply arrayOfVariantOfDouble286

Set move4 = product6.Move

Set move4 = move4.MovableObject

Dim arrayOfVariantOfDouble287(11)
arrayOfVariantOfDouble287(0) = 1.000000
arrayOfVariantOfDouble287(1) = 0.000000
arrayOfVariantOfDouble287(2) = 0.000000
arrayOfVariantOfDouble287(3) = 0.000000
arrayOfVariantOfDouble287(4) = 1.000000
arrayOfVariantOfDouble287(5) = 0.000000
arrayOfVariantOfDouble287(6) = 0.000000
arrayOfVariantOfDouble287(7) = 0.000000
arrayOfVariantOfDouble287(8) = 1.000000
arrayOfVariantOfDouble287(9) = 0.000000
arrayOfVariantOfDouble287(10) = 2.452608
arrayOfVariantOfDouble287(11) = 0.000000
move4.Apply arrayOfVariantOfDouble287

Set move4 = product6.Move

Set move4 = move4.MovableObject

Dim arrayOfVariantOfDouble288(11)
arrayOfVariantOfDouble288(0) = 1.000000
arrayOfVariantOfDouble288(1) = 0.000000
arrayOfVariantOfDouble288(2) = 0.000000
arrayOfVariantOfDouble288(3) = 0.000000
arrayOfVariantOfDouble288(4) = 1.000000
arrayOfVariantOfDouble288(5) = 0.000000
arrayOfVariantOfDouble288(6) = 0.000000
arrayOfVariantOfDouble288(7) = 0.000000
arrayOfVariantOfDouble288(8) = 1.000000
arrayOfVariantOfDouble288(9) = 0.000000
arrayOfVariantOfDouble288(10) = 4.963135
arrayOfVariantOfDouble288(11) = 0.000000
move4.Apply arrayOfVariantOfDouble288

Set move4 = product6.Move

Set move4 = move4.MovableObject

Dim arrayOfVariantOfDouble289(11)
arrayOfVariantOfDouble289(0) = 1.000000
arrayOfVariantOfDouble289(1) = 0.000000
arrayOfVariantOfDouble289(2) = 0.000000
arrayOfVariantOfDouble289(3) = 0.000000
arrayOfVariantOfDouble289(4) = 1.000000
arrayOfVariantOfDouble289(5) = 0.000000
arrayOfVariantOfDouble289(6) = 0.000000
arrayOfVariantOfDouble289(7) = 0.000000
arrayOfVariantOfDouble289(8) = 1.000000
arrayOfVariantOfDouble289(9) = 0.000000
arrayOfVariantOfDouble289(10) = 2.452601
arrayOfVariantOfDouble289(11) = 0.000000
move4.Apply arrayOfVariantOfDouble289

Set move4 = product6.Move

Set move4 = move4.MovableObject

Dim arrayOfVariantOfDouble290(11)
arrayOfVariantOfDouble290(0) = 1.000000
arrayOfVariantOfDouble290(1) = 0.000000
arrayOfVariantOfDouble290(2) = 0.000000
arrayOfVariantOfDouble290(3) = 0.000000
arrayOfVariantOfDouble290(4) = 1.000000
arrayOfVariantOfDouble290(5) = 0.000000
arrayOfVariantOfDouble290(6) = 0.000000
arrayOfVariantOfDouble290(7) = 0.000000
arrayOfVariantOfDouble290(8) = 1.000000
arrayOfVariantOfDouble290(9) = 0.000000
arrayOfVariantOfDouble290(10) = 3.308752
arrayOfVariantOfDouble290(11) = 0.000000
move4.Apply arrayOfVariantOfDouble290

Set move4 = product6.Move

Set move4 = move4.MovableObject

Dim arrayOfVariantOfDouble291(11)
arrayOfVariantOfDouble291(0) = 1.000000
arrayOfVariantOfDouble291(1) = 0.000000
arrayOfVariantOfDouble291(2) = 0.000000
arrayOfVariantOfDouble291(3) = 0.000000
arrayOfVariantOfDouble291(4) = 1.000000
arrayOfVariantOfDouble291(5) = 0.000000
arrayOfVariantOfDouble291(6) = 0.000000
arrayOfVariantOfDouble291(7) = 0.000000
arrayOfVariantOfDouble291(8) = 1.000000
arrayOfVariantOfDouble291(9) = 0.000000
arrayOfVariantOfDouble291(10) = 4.106991
arrayOfVariantOfDouble291(11) = 0.000000
move4.Apply arrayOfVariantOfDouble291

Set move4 = product6.Move

Set move4 = move4.MovableObject

Dim arrayOfVariantOfDouble292(11)
arrayOfVariantOfDouble292(0) = 1.000000
arrayOfVariantOfDouble292(1) = 0.000000
arrayOfVariantOfDouble292(2) = 0.000000
arrayOfVariantOfDouble292(3) = 0.000000
arrayOfVariantOfDouble292(4) = 1.000000
arrayOfVariantOfDouble292(5) = 0.000000
arrayOfVariantOfDouble292(6) = 0.000000
arrayOfVariantOfDouble292(7) = 0.000000
arrayOfVariantOfDouble292(8) = 1.000000
arrayOfVariantOfDouble292(9) = 0.000000
arrayOfVariantOfDouble292(10) = 3.308749
arrayOfVariantOfDouble292(11) = 0.000000
move4.Apply arrayOfVariantOfDouble292

Set move4 = product6.Move

Set move4 = move4.MovableObject

Dim arrayOfVariantOfDouble293(11)
arrayOfVariantOfDouble293(0) = 1.000000
arrayOfVariantOfDouble293(1) = 0.000000
arrayOfVariantOfDouble293(2) = 0.000000
arrayOfVariantOfDouble293(3) = 0.000000
arrayOfVariantOfDouble293(4) = 1.000000
arrayOfVariantOfDouble293(5) = 0.000000
arrayOfVariantOfDouble293(6) = 0.000000
arrayOfVariantOfDouble293(7) = 0.000000
arrayOfVariantOfDouble293(8) = 1.000000
arrayOfVariantOfDouble293(9) = 0.000000
arrayOfVariantOfDouble293(10) = 5.761352
arrayOfVariantOfDouble293(11) = 0.000000
move4.Apply arrayOfVariantOfDouble293

Set move4 = product6.Move

Set move4 = move4.MovableObject

Dim arrayOfVariantOfDouble294(11)
arrayOfVariantOfDouble294(0) = 1.000000
arrayOfVariantOfDouble294(1) = 0.000000
arrayOfVariantOfDouble294(2) = 0.000000
arrayOfVariantOfDouble294(3) = 0.000000
arrayOfVariantOfDouble294(4) = 1.000000
arrayOfVariantOfDouble294(5) = 0.000000
arrayOfVariantOfDouble294(6) = 0.000000
arrayOfVariantOfDouble294(7) = 0.000000
arrayOfVariantOfDouble294(8) = 1.000000
arrayOfVariantOfDouble294(9) = 0.000000
arrayOfVariantOfDouble294(10) = 4.106992
arrayOfVariantOfDouble294(11) = 0.000000
move4.Apply arrayOfVariantOfDouble294

Set move4 = product6.Move

Set move4 = move4.MovableObject

Dim arrayOfVariantOfDouble295(11)
arrayOfVariantOfDouble295(0) = 1.000000
arrayOfVariantOfDouble295(1) = 0.000000
arrayOfVariantOfDouble295(2) = 0.000000
arrayOfVariantOfDouble295(3) = 0.000000
arrayOfVariantOfDouble295(4) = 1.000000
arrayOfVariantOfDouble295(5) = 0.000000
arrayOfVariantOfDouble295(6) = 0.000000
arrayOfVariantOfDouble295(7) = 0.000000
arrayOfVariantOfDouble295(8) = 1.000000
arrayOfVariantOfDouble295(9) = 0.000000
arrayOfVariantOfDouble295(10) = 4.963119
arrayOfVariantOfDouble295(11) = 0.000000
move4.Apply arrayOfVariantOfDouble295

Set move4 = product6.Move

Set move4 = move4.MovableObject

Dim arrayOfVariantOfDouble296(11)
arrayOfVariantOfDouble296(0) = 1.000000
arrayOfVariantOfDouble296(1) = 0.000000
arrayOfVariantOfDouble296(2) = 0.000000
arrayOfVariantOfDouble296(3) = 0.000000
arrayOfVariantOfDouble296(4) = 1.000000
arrayOfVariantOfDouble296(5) = 0.000000
arrayOfVariantOfDouble296(6) = 0.000000
arrayOfVariantOfDouble296(7) = 0.000000
arrayOfVariantOfDouble296(8) = 1.000000
arrayOfVariantOfDouble296(9) = 0.000000
arrayOfVariantOfDouble296(10) = 2.452613
arrayOfVariantOfDouble296(11) = 0.000000
move4.Apply arrayOfVariantOfDouble296

Set move4 = product6.Move

Set move4 = move4.MovableObject

Dim arrayOfVariantOfDouble297(11)
arrayOfVariantOfDouble297(0) = 1.000000
arrayOfVariantOfDouble297(1) = 0.000000
arrayOfVariantOfDouble297(2) = 0.000000
arrayOfVariantOfDouble297(3) = 0.000000
arrayOfVariantOfDouble297(4) = 1.000000
arrayOfVariantOfDouble297(5) = 0.000000
arrayOfVariantOfDouble297(6) = 0.000000
arrayOfVariantOfDouble297(7) = 0.000000
arrayOfVariantOfDouble297(8) = 1.000000
arrayOfVariantOfDouble297(9) = 0.000000
arrayOfVariantOfDouble297(10) = 5.761349
arrayOfVariantOfDouble297(11) = 0.000000
move4.Apply arrayOfVariantOfDouble297

Set move4 = product6.Move

Set move4 = move4.MovableObject

Dim arrayOfVariantOfDouble298(11)
arrayOfVariantOfDouble298(0) = 1.000000
arrayOfVariantOfDouble298(1) = 0.000000
arrayOfVariantOfDouble298(2) = 0.000000
arrayOfVariantOfDouble298(3) = 0.000000
arrayOfVariantOfDouble298(4) = 1.000000
arrayOfVariantOfDouble298(5) = 0.000000
arrayOfVariantOfDouble298(6) = 0.000000
arrayOfVariantOfDouble298(7) = 0.000000
arrayOfVariantOfDouble298(8) = 1.000000
arrayOfVariantOfDouble298(9) = 0.000000
arrayOfVariantOfDouble298(10) = 4.106984
arrayOfVariantOfDouble298(11) = 0.000000
move4.Apply arrayOfVariantOfDouble298

Set move4 = product6.Move

Set move4 = move4.MovableObject

Dim arrayOfVariantOfDouble299(11)
arrayOfVariantOfDouble299(0) = 1.000000
arrayOfVariantOfDouble299(1) = 0.000000
arrayOfVariantOfDouble299(2) = 0.000000
arrayOfVariantOfDouble299(3) = 0.000000
arrayOfVariantOfDouble299(4) = 1.000000
arrayOfVariantOfDouble299(5) = 0.000000
arrayOfVariantOfDouble299(6) = 0.000000
arrayOfVariantOfDouble299(7) = 0.000000
arrayOfVariantOfDouble299(8) = 1.000000
arrayOfVariantOfDouble299(9) = 0.000000
arrayOfVariantOfDouble299(10) = 2.510545
arrayOfVariantOfDouble299(11) = 0.000000
move4.Apply arrayOfVariantOfDouble299

Set move4 = product6.Move

Set move4 = move4.MovableObject

Dim arrayOfVariantOfDouble300(11)
arrayOfVariantOfDouble300(0) = 1.000000
arrayOfVariantOfDouble300(1) = 0.000000
arrayOfVariantOfDouble300(2) = 0.000000
arrayOfVariantOfDouble300(3) = 0.000000
arrayOfVariantOfDouble300(4) = 1.000000
arrayOfVariantOfDouble300(5) = 0.000000
arrayOfVariantOfDouble300(6) = 0.000000
arrayOfVariantOfDouble300(7) = 0.000000
arrayOfVariantOfDouble300(8) = 1.000000
arrayOfVariantOfDouble300(9) = 0.000000
arrayOfVariantOfDouble300(10) = 2.452595
arrayOfVariantOfDouble300(11) = 0.000000
move4.Apply arrayOfVariantOfDouble300

Set move4 = product6.Move

Set move4 = move4.MovableObject

Dim arrayOfVariantOfDouble301(11)
arrayOfVariantOfDouble301(0) = 1.000000
arrayOfVariantOfDouble301(1) = 0.000000
arrayOfVariantOfDouble301(2) = 0.000000
arrayOfVariantOfDouble301(3) = 0.000000
arrayOfVariantOfDouble301(4) = 1.000000
arrayOfVariantOfDouble301(5) = 0.000000
arrayOfVariantOfDouble301(6) = 0.000000
arrayOfVariantOfDouble301(7) = 0.000000
arrayOfVariantOfDouble301(8) = 1.000000
arrayOfVariantOfDouble301(9) = 0.000000
arrayOfVariantOfDouble301(10) = 1.654374
arrayOfVariantOfDouble301(11) = 0.000000
move4.Apply arrayOfVariantOfDouble301

Set move4 = product6.Move

Set move4 = move4.MovableObject

Dim arrayOfVariantOfDouble302(11)
arrayOfVariantOfDouble302(0) = 1.000000
arrayOfVariantOfDouble302(1) = 0.000000
arrayOfVariantOfDouble302(2) = 0.000000
arrayOfVariantOfDouble302(3) = 0.000000
arrayOfVariantOfDouble302(4) = 1.000000
arrayOfVariantOfDouble302(5) = 0.000000
arrayOfVariantOfDouble302(6) = 0.000000
arrayOfVariantOfDouble302(7) = 0.000000
arrayOfVariantOfDouble302(8) = 1.000000
arrayOfVariantOfDouble302(9) = 0.000000
arrayOfVariantOfDouble302(10) = 3.308775
arrayOfVariantOfDouble302(11) = 0.000000
move4.Apply arrayOfVariantOfDouble302

Set move4 = product6.Move

Set move4 = move4.MovableObject

Dim arrayOfVariantOfDouble303(11)
arrayOfVariantOfDouble303(0) = 1.000000
arrayOfVariantOfDouble303(1) = 0.000000
arrayOfVariantOfDouble303(2) = 0.000000
arrayOfVariantOfDouble303(3) = 0.000000
arrayOfVariantOfDouble303(4) = 1.000000
arrayOfVariantOfDouble303(5) = 0.000000
arrayOfVariantOfDouble303(6) = 0.000000
arrayOfVariantOfDouble303(7) = 0.000000
arrayOfVariantOfDouble303(8) = 1.000000
arrayOfVariantOfDouble303(9) = 0.000000
arrayOfVariantOfDouble303(10) = 1.654370
arrayOfVariantOfDouble303(11) = 0.000000
move4.Apply arrayOfVariantOfDouble303

Set move4 = product6.Move

Set move4 = move4.MovableObject

Dim arrayOfVariantOfDouble304(11)
arrayOfVariantOfDouble304(0) = 1.000000
arrayOfVariantOfDouble304(1) = 0.000000
arrayOfVariantOfDouble304(2) = 0.000000
arrayOfVariantOfDouble304(3) = 0.000000
arrayOfVariantOfDouble304(4) = 1.000000
arrayOfVariantOfDouble304(5) = 0.000000
arrayOfVariantOfDouble304(6) = 0.000000
arrayOfVariantOfDouble304(7) = 0.000000
arrayOfVariantOfDouble304(8) = 1.000000
arrayOfVariantOfDouble304(9) = 0.000000
arrayOfVariantOfDouble304(10) = 3.308758
arrayOfVariantOfDouble304(11) = 0.000000
move4.Apply arrayOfVariantOfDouble304

Set move4 = product6.Move

Set move4 = move4.MovableObject

Dim arrayOfVariantOfDouble305(11)
arrayOfVariantOfDouble305(0) = 1.000000
arrayOfVariantOfDouble305(1) = 0.000000
arrayOfVariantOfDouble305(2) = 0.000000
arrayOfVariantOfDouble305(3) = 0.000000
arrayOfVariantOfDouble305(4) = 1.000000
arrayOfVariantOfDouble305(5) = 0.000000
arrayOfVariantOfDouble305(6) = 0.000000
arrayOfVariantOfDouble305(7) = 0.000000
arrayOfVariantOfDouble305(8) = 1.000000
arrayOfVariantOfDouble305(9) = 0.000000
arrayOfVariantOfDouble305(10) = 4.164911
arrayOfVariantOfDouble305(11) = 0.000000
move4.Apply arrayOfVariantOfDouble305

Set move4 = product6.Move

Set move4 = move4.MovableObject

Dim arrayOfVariantOfDouble306(11)
arrayOfVariantOfDouble306(0) = 1.000000
arrayOfVariantOfDouble306(1) = 0.000000
arrayOfVariantOfDouble306(2) = 0.000000
arrayOfVariantOfDouble306(3) = 0.000000
arrayOfVariantOfDouble306(4) = 1.000000
arrayOfVariantOfDouble306(5) = 0.000000
arrayOfVariantOfDouble306(6) = 0.000000
arrayOfVariantOfDouble306(7) = 0.000000
arrayOfVariantOfDouble306(8) = 1.000000
arrayOfVariantOfDouble306(9) = 0.000000
arrayOfVariantOfDouble306(10) = 2.452600
arrayOfVariantOfDouble306(11) = 0.000000
move4.Apply arrayOfVariantOfDouble306

Set move4 = product6.Move

Set move4 = move4.MovableObject

Dim arrayOfVariantOfDouble307(11)
arrayOfVariantOfDouble307(0) = 1.000000
arrayOfVariantOfDouble307(1) = 0.000000
arrayOfVariantOfDouble307(2) = 0.000000
arrayOfVariantOfDouble307(3) = 0.000000
arrayOfVariantOfDouble307(4) = 1.000000
arrayOfVariantOfDouble307(5) = 0.000000
arrayOfVariantOfDouble307(6) = 0.000000
arrayOfVariantOfDouble307(7) = 0.000000
arrayOfVariantOfDouble307(8) = 1.000000
arrayOfVariantOfDouble307(9) = 0.000000
arrayOfVariantOfDouble307(10) = 5.761369
arrayOfVariantOfDouble307(11) = 0.000000
move4.Apply arrayOfVariantOfDouble307

Set move4 = product6.Move

Set move4 = move4.MovableObject

Dim arrayOfVariantOfDouble308(11)
arrayOfVariantOfDouble308(0) = 1.000000
arrayOfVariantOfDouble308(1) = 0.000000
arrayOfVariantOfDouble308(2) = 0.000000
arrayOfVariantOfDouble308(3) = 0.000000
arrayOfVariantOfDouble308(4) = 1.000000
arrayOfVariantOfDouble308(5) = 0.000000
arrayOfVariantOfDouble308(6) = 0.000000
arrayOfVariantOfDouble308(7) = 0.000000
arrayOfVariantOfDouble308(8) = 1.000000
arrayOfVariantOfDouble308(9) = 0.000000
arrayOfVariantOfDouble308(10) = 4.963131
arrayOfVariantOfDouble308(11) = 0.000000
move4.Apply arrayOfVariantOfDouble308

Set move4 = product6.Move

Set move4 = move4.MovableObject

Dim arrayOfVariantOfDouble309(11)
arrayOfVariantOfDouble309(0) = 1.000000
arrayOfVariantOfDouble309(1) = 0.000000
arrayOfVariantOfDouble309(2) = 0.000000
arrayOfVariantOfDouble309(3) = 0.000000
arrayOfVariantOfDouble309(4) = 1.000000
arrayOfVariantOfDouble309(5) = 0.000000
arrayOfVariantOfDouble309(6) = 0.000000
arrayOfVariantOfDouble309(7) = 0.000000
arrayOfVariantOfDouble309(8) = 1.000000
arrayOfVariantOfDouble309(9) = 0.000000
arrayOfVariantOfDouble309(10) = 6.617517
arrayOfVariantOfDouble309(11) = 0.000000
move4.Apply arrayOfVariantOfDouble309

Set move4 = product6.Move

Set move4 = move4.MovableObject

Dim arrayOfVariantOfDouble310(11)
arrayOfVariantOfDouble310(0) = 1.000000
arrayOfVariantOfDouble310(1) = 0.000000
arrayOfVariantOfDouble310(2) = 0.000000
arrayOfVariantOfDouble310(3) = 0.000000
arrayOfVariantOfDouble310(4) = 1.000000
arrayOfVariantOfDouble310(5) = 0.000000
arrayOfVariantOfDouble310(6) = 0.000000
arrayOfVariantOfDouble310(7) = 0.000000
arrayOfVariantOfDouble310(8) = 1.000000
arrayOfVariantOfDouble310(9) = 0.000000
arrayOfVariantOfDouble310(10) = 4.963119
arrayOfVariantOfDouble310(11) = 0.000000
move4.Apply arrayOfVariantOfDouble310

Set move4 = product6.Move

Set move4 = move4.MovableObject

Dim arrayOfVariantOfDouble311(11)
arrayOfVariantOfDouble311(0) = 1.000000
arrayOfVariantOfDouble311(1) = 0.000000
arrayOfVariantOfDouble311(2) = 0.000000
arrayOfVariantOfDouble311(3) = 0.000000
arrayOfVariantOfDouble311(4) = 1.000000
arrayOfVariantOfDouble311(5) = 0.000000
arrayOfVariantOfDouble311(6) = 0.000000
arrayOfVariantOfDouble311(7) = 0.000000
arrayOfVariantOfDouble311(8) = 1.000000
arrayOfVariantOfDouble311(9) = 0.000000
arrayOfVariantOfDouble311(10) = 4.905217
arrayOfVariantOfDouble311(11) = 0.000000
move4.Apply arrayOfVariantOfDouble311

Set move4 = product6.Move

Set move4 = move4.MovableObject

Dim arrayOfVariantOfDouble312(11)
arrayOfVariantOfDouble312(0) = 1.000000
arrayOfVariantOfDouble312(1) = 0.000000
arrayOfVariantOfDouble312(2) = 0.000000
arrayOfVariantOfDouble312(3) = 0.000000
arrayOfVariantOfDouble312(4) = 1.000000
arrayOfVariantOfDouble312(5) = 0.000000
arrayOfVariantOfDouble312(6) = 0.000000
arrayOfVariantOfDouble312(7) = 0.000000
arrayOfVariantOfDouble312(8) = 1.000000
arrayOfVariantOfDouble312(9) = 0.000000
arrayOfVariantOfDouble312(10) = 7.415737
arrayOfVariantOfDouble312(11) = 0.000000
move4.Apply arrayOfVariantOfDouble312

Set move4 = product6.Move

Set move4 = move4.MovableObject

Dim arrayOfVariantOfDouble313(11)
arrayOfVariantOfDouble313(0) = 1.000000
arrayOfVariantOfDouble313(1) = 0.000000
arrayOfVariantOfDouble313(2) = 0.000000
arrayOfVariantOfDouble313(3) = 0.000000
arrayOfVariantOfDouble313(4) = 1.000000
arrayOfVariantOfDouble313(5) = 0.000000
arrayOfVariantOfDouble313(6) = 0.000000
arrayOfVariantOfDouble313(7) = 0.000000
arrayOfVariantOfDouble313(8) = 1.000000
arrayOfVariantOfDouble313(9) = 0.000000
arrayOfVariantOfDouble313(10) = 4.106991
arrayOfVariantOfDouble313(11) = 0.000000
move4.Apply arrayOfVariantOfDouble313

Set move4 = product6.Move

Set move4 = move4.MovableObject

Dim arrayOfVariantOfDouble314(11)
arrayOfVariantOfDouble314(0) = 1.000000
arrayOfVariantOfDouble314(1) = 0.000000
arrayOfVariantOfDouble314(2) = 0.000000
arrayOfVariantOfDouble314(3) = 0.000000
arrayOfVariantOfDouble314(4) = 1.000000
arrayOfVariantOfDouble314(5) = 0.000000
arrayOfVariantOfDouble314(6) = 0.000000
arrayOfVariantOfDouble314(7) = 0.000000
arrayOfVariantOfDouble314(8) = 1.000000
arrayOfVariantOfDouble314(9) = 0.000000
arrayOfVariantOfDouble314(10) = 4.106953
arrayOfVariantOfDouble314(11) = 0.000000
move4.Apply arrayOfVariantOfDouble314

Set move4 = product6.Move

Set move4 = move4.MovableObject

Dim arrayOfVariantOfDouble315(11)
arrayOfVariantOfDouble315(0) = 1.000000
arrayOfVariantOfDouble315(1) = 0.000000
arrayOfVariantOfDouble315(2) = 0.000000
arrayOfVariantOfDouble315(3) = 0.000000
arrayOfVariantOfDouble315(4) = 1.000000
arrayOfVariantOfDouble315(5) = 0.000000
arrayOfVariantOfDouble315(6) = 0.000000
arrayOfVariantOfDouble315(7) = 0.000000
arrayOfVariantOfDouble315(8) = 1.000000
arrayOfVariantOfDouble315(9) = 0.000000
arrayOfVariantOfDouble315(10) = 5.761372
arrayOfVariantOfDouble315(11) = 0.000000
move4.Apply arrayOfVariantOfDouble315

Set move4 = product6.Move

Set move4 = move4.MovableObject

Dim arrayOfVariantOfDouble316(11)
arrayOfVariantOfDouble316(0) = 1.000000
arrayOfVariantOfDouble316(1) = 0.000000
arrayOfVariantOfDouble316(2) = 0.000000
arrayOfVariantOfDouble316(3) = 0.000000
arrayOfVariantOfDouble316(4) = 1.000000
arrayOfVariantOfDouble316(5) = 0.000000
arrayOfVariantOfDouble316(6) = 0.000000
arrayOfVariantOfDouble316(7) = 0.000000
arrayOfVariantOfDouble316(8) = 1.000000
arrayOfVariantOfDouble316(9) = 0.000000
arrayOfVariantOfDouble316(10) = 4.905196
arrayOfVariantOfDouble316(11) = 0.000000
move4.Apply arrayOfVariantOfDouble316

Set move4 = product6.Move

Set move4 = move4.MovableObject

Dim arrayOfVariantOfDouble317(11)
arrayOfVariantOfDouble317(0) = 1.000000
arrayOfVariantOfDouble317(1) = 0.000000
arrayOfVariantOfDouble317(2) = 0.000000
arrayOfVariantOfDouble317(3) = 0.000000
arrayOfVariantOfDouble317(4) = 1.000000
arrayOfVariantOfDouble317(5) = 0.000000
arrayOfVariantOfDouble317(6) = 0.000000
arrayOfVariantOfDouble317(7) = 0.000000
arrayOfVariantOfDouble317(8) = 1.000000
arrayOfVariantOfDouble317(9) = 0.000000
arrayOfVariantOfDouble317(10) = 7.415732
arrayOfVariantOfDouble317(11) = 0.000000
move4.Apply arrayOfVariantOfDouble317

Set move4 = product6.Move

Set move4 = move4.MovableObject

Dim arrayOfVariantOfDouble318(11)
arrayOfVariantOfDouble318(0) = 1.000000
arrayOfVariantOfDouble318(1) = 0.000000
arrayOfVariantOfDouble318(2) = 0.000000
arrayOfVariantOfDouble318(3) = 0.000000
arrayOfVariantOfDouble318(4) = 1.000000
arrayOfVariantOfDouble318(5) = 0.000000
arrayOfVariantOfDouble318(6) = 0.000000
arrayOfVariantOfDouble318(7) = 0.000000
arrayOfVariantOfDouble318(8) = 1.000000
arrayOfVariantOfDouble318(9) = 0.000000
arrayOfVariantOfDouble318(10) = 4.905219
arrayOfVariantOfDouble318(11) = 0.000000
move4.Apply arrayOfVariantOfDouble318

Set move4 = product6.Move

Set move4 = move4.MovableObject

Dim arrayOfVariantOfDouble319(11)
arrayOfVariantOfDouble319(0) = 1.000000
arrayOfVariantOfDouble319(1) = 0.000000
arrayOfVariantOfDouble319(2) = 0.000000
arrayOfVariantOfDouble319(3) = 0.000000
arrayOfVariantOfDouble319(4) = 1.000000
arrayOfVariantOfDouble319(5) = 0.000000
arrayOfVariantOfDouble319(6) = 0.000000
arrayOfVariantOfDouble319(7) = 0.000000
arrayOfVariantOfDouble319(8) = 1.000000
arrayOfVariantOfDouble319(9) = 0.000000
arrayOfVariantOfDouble319(10) = 7.357775
arrayOfVariantOfDouble319(11) = 0.000000
move4.Apply arrayOfVariantOfDouble319

Set move4 = product6.Move

Set move4 = move4.MovableObject

Dim arrayOfVariantOfDouble320(11)
arrayOfVariantOfDouble320(0) = 1.000000
arrayOfVariantOfDouble320(1) = 0.000000
arrayOfVariantOfDouble320(2) = 0.000000
arrayOfVariantOfDouble320(3) = 0.000000
arrayOfVariantOfDouble320(4) = 1.000000
arrayOfVariantOfDouble320(5) = 0.000000
arrayOfVariantOfDouble320(6) = 0.000000
arrayOfVariantOfDouble320(7) = 0.000000
arrayOfVariantOfDouble320(8) = 1.000000
arrayOfVariantOfDouble320(9) = 0.000000
arrayOfVariantOfDouble320(10) = 7.415745
arrayOfVariantOfDouble320(11) = 0.000000
move4.Apply arrayOfVariantOfDouble320

Set move4 = product6.Move

Set move4 = move4.MovableObject

Dim arrayOfVariantOfDouble321(11)
arrayOfVariantOfDouble321(0) = 1.000000
arrayOfVariantOfDouble321(1) = 0.000000
arrayOfVariantOfDouble321(2) = 0.000000
arrayOfVariantOfDouble321(3) = 0.000000
arrayOfVariantOfDouble321(4) = 1.000000
arrayOfVariantOfDouble321(5) = 0.000000
arrayOfVariantOfDouble321(6) = 0.000000
arrayOfVariantOfDouble321(7) = 0.000000
arrayOfVariantOfDouble321(8) = 1.000000
arrayOfVariantOfDouble321(9) = 0.000000
arrayOfVariantOfDouble321(10) = 9.810395
arrayOfVariantOfDouble321(11) = 0.000000
move4.Apply arrayOfVariantOfDouble321

Set move4 = product6.Move

Set move4 = move4.MovableObject

Dim arrayOfVariantOfDouble322(11)
arrayOfVariantOfDouble322(0) = 1.000000
arrayOfVariantOfDouble322(1) = 0.000000
arrayOfVariantOfDouble322(2) = 0.000000
arrayOfVariantOfDouble322(3) = 0.000000
arrayOfVariantOfDouble322(4) = 1.000000
arrayOfVariantOfDouble322(5) = 0.000000
arrayOfVariantOfDouble322(6) = 0.000000
arrayOfVariantOfDouble322(7) = 0.000000
arrayOfVariantOfDouble322(8) = 1.000000
arrayOfVariantOfDouble322(9) = 0.000000
arrayOfVariantOfDouble322(10) = 9.012176
arrayOfVariantOfDouble322(11) = 0.000000
move4.Apply arrayOfVariantOfDouble322

Set move4 = product6.Move

Set move4 = move4.MovableObject

Dim arrayOfVariantOfDouble323(11)
arrayOfVariantOfDouble323(0) = 1.000000
arrayOfVariantOfDouble323(1) = 0.000000
arrayOfVariantOfDouble323(2) = 0.000000
arrayOfVariantOfDouble323(3) = 0.000000
arrayOfVariantOfDouble323(4) = 1.000000
arrayOfVariantOfDouble323(5) = 0.000000
arrayOfVariantOfDouble323(6) = 0.000000
arrayOfVariantOfDouble323(7) = 0.000000
arrayOfVariantOfDouble323(8) = 1.000000
arrayOfVariantOfDouble323(9) = 0.000000
arrayOfVariantOfDouble323(10) = 9.810395
arrayOfVariantOfDouble323(11) = 0.000000
move4.Apply arrayOfVariantOfDouble323

Set move4 = product6.Move

Set move4 = move4.MovableObject

Dim arrayOfVariantOfDouble324(11)
arrayOfVariantOfDouble324(0) = 1.000000
arrayOfVariantOfDouble324(1) = 0.000000
arrayOfVariantOfDouble324(2) = 0.000000
arrayOfVariantOfDouble324(3) = 0.000000
arrayOfVariantOfDouble324(4) = 1.000000
arrayOfVariantOfDouble324(5) = 0.000000
arrayOfVariantOfDouble324(6) = 0.000000
arrayOfVariantOfDouble324(7) = 0.000000
arrayOfVariantOfDouble324(8) = 1.000000
arrayOfVariantOfDouble324(9) = 0.000000
arrayOfVariantOfDouble324(10) = 14.715617
arrayOfVariantOfDouble324(11) = 0.000000
move4.Apply arrayOfVariantOfDouble324

Set move4 = product6.Move

Set move4 = move4.MovableObject

Dim arrayOfVariantOfDouble325(11)
arrayOfVariantOfDouble325(0) = 1.000000
arrayOfVariantOfDouble325(1) = 0.000000
arrayOfVariantOfDouble325(2) = 0.000000
arrayOfVariantOfDouble325(3) = 0.000000
arrayOfVariantOfDouble325(4) = 1.000000
arrayOfVariantOfDouble325(5) = 0.000000
arrayOfVariantOfDouble325(6) = 0.000000
arrayOfVariantOfDouble325(7) = 0.000000
arrayOfVariantOfDouble325(8) = 1.000000
arrayOfVariantOfDouble325(9) = 0.000000
arrayOfVariantOfDouble325(10) = 9.012175
arrayOfVariantOfDouble325(11) = 0.000000
move4.Apply arrayOfVariantOfDouble325

Set move4 = product6.Move

Set move4 = move4.MovableObject

Dim arrayOfVariantOfDouble326(11)
arrayOfVariantOfDouble326(0) = 1.000000
arrayOfVariantOfDouble326(1) = 0.000000
arrayOfVariantOfDouble326(2) = 0.000000
arrayOfVariantOfDouble326(3) = 0.000000
arrayOfVariantOfDouble326(4) = 1.000000
arrayOfVariantOfDouble326(5) = 0.000000
arrayOfVariantOfDouble326(6) = 0.000000
arrayOfVariantOfDouble326(7) = 0.000000
arrayOfVariantOfDouble326(8) = 1.000000
arrayOfVariantOfDouble326(9) = 0.000000
arrayOfVariantOfDouble326(10) = 9.810394
arrayOfVariantOfDouble326(11) = 0.000000
move4.Apply arrayOfVariantOfDouble326

Set move4 = product6.Move

Set move4 = move4.MovableObject

Dim arrayOfVariantOfDouble327(11)
arrayOfVariantOfDouble327(0) = 1.000000
arrayOfVariantOfDouble327(1) = 0.000000
arrayOfVariantOfDouble327(2) = 0.000000
arrayOfVariantOfDouble327(3) = 0.000000
arrayOfVariantOfDouble327(4) = 1.000000
arrayOfVariantOfDouble327(5) = 0.000000
arrayOfVariantOfDouble327(6) = 0.000000
arrayOfVariantOfDouble327(7) = 0.000000
arrayOfVariantOfDouble327(8) = 1.000000
arrayOfVariantOfDouble327(9) = 0.000000
arrayOfVariantOfDouble327(10) = 8.954231
arrayOfVariantOfDouble327(11) = 0.000000
move4.Apply arrayOfVariantOfDouble327

Set move4 = product6.Move

Set move4 = move4.MovableObject

Dim arrayOfVariantOfDouble328(11)
arrayOfVariantOfDouble328(0) = 1.000000
arrayOfVariantOfDouble328(1) = 0.000000
arrayOfVariantOfDouble328(2) = 0.000000
arrayOfVariantOfDouble328(3) = 0.000000
arrayOfVariantOfDouble328(4) = 1.000000
arrayOfVariantOfDouble328(5) = 0.000000
arrayOfVariantOfDouble328(6) = 0.000000
arrayOfVariantOfDouble328(7) = 0.000000
arrayOfVariantOfDouble328(8) = 1.000000
arrayOfVariantOfDouble328(9) = 0.000000
arrayOfVariantOfDouble328(10) = 7.357818
arrayOfVariantOfDouble328(11) = 0.000000
move4.Apply arrayOfVariantOfDouble328

Set move4 = product6.Move

Set move4 = move4.MovableObject

Dim arrayOfVariantOfDouble329(11)
arrayOfVariantOfDouble329(0) = 1.000000
arrayOfVariantOfDouble329(1) = 0.000000
arrayOfVariantOfDouble329(2) = 0.000000
arrayOfVariantOfDouble329(3) = 0.000000
arrayOfVariantOfDouble329(4) = 1.000000
arrayOfVariantOfDouble329(5) = 0.000000
arrayOfVariantOfDouble329(6) = 0.000000
arrayOfVariantOfDouble329(7) = 0.000000
arrayOfVariantOfDouble329(8) = 1.000000
arrayOfVariantOfDouble329(9) = 0.000000
arrayOfVariantOfDouble329(10) = 6.559567
arrayOfVariantOfDouble329(11) = 0.000000
move4.Apply arrayOfVariantOfDouble329

Set move4 = product6.Move

Set move4 = move4.MovableObject

Dim arrayOfVariantOfDouble330(11)
arrayOfVariantOfDouble330(0) = 1.000000
arrayOfVariantOfDouble330(1) = 0.000000
arrayOfVariantOfDouble330(2) = 0.000000
arrayOfVariantOfDouble330(3) = 0.000000
arrayOfVariantOfDouble330(4) = 1.000000
arrayOfVariantOfDouble330(5) = 0.000000
arrayOfVariantOfDouble330(6) = 0.000000
arrayOfVariantOfDouble330(7) = 0.000000
arrayOfVariantOfDouble330(8) = 1.000000
arrayOfVariantOfDouble330(9) = 0.000000
arrayOfVariantOfDouble330(10) = 5.703427
arrayOfVariantOfDouble330(11) = 0.000000
move4.Apply arrayOfVariantOfDouble330

Set move4 = product6.Move

Set move4 = move4.MovableObject

Dim arrayOfVariantOfDouble331(11)
arrayOfVariantOfDouble331(0) = 1.000000
arrayOfVariantOfDouble331(1) = 0.000000
arrayOfVariantOfDouble331(2) = 0.000000
arrayOfVariantOfDouble331(3) = 0.000000
arrayOfVariantOfDouble331(4) = 1.000000
arrayOfVariantOfDouble331(5) = 0.000000
arrayOfVariantOfDouble331(6) = 0.000000
arrayOfVariantOfDouble331(7) = 0.000000
arrayOfVariantOfDouble331(8) = 1.000000
arrayOfVariantOfDouble331(9) = 0.000000
arrayOfVariantOfDouble331(10) = 5.761339
arrayOfVariantOfDouble331(11) = 0.000000
move4.Apply arrayOfVariantOfDouble331

Set move4 = product6.Move

Set move4 = move4.MovableObject

Dim arrayOfVariantOfDouble332(11)
arrayOfVariantOfDouble332(0) = 1.000000
arrayOfVariantOfDouble332(1) = 0.000000
arrayOfVariantOfDouble332(2) = 0.000000
arrayOfVariantOfDouble332(3) = 0.000000
arrayOfVariantOfDouble332(4) = 1.000000
arrayOfVariantOfDouble332(5) = 0.000000
arrayOfVariantOfDouble332(6) = 0.000000
arrayOfVariantOfDouble332(7) = 0.000000
arrayOfVariantOfDouble332(8) = 1.000000
arrayOfVariantOfDouble332(9) = 0.000000
arrayOfVariantOfDouble332(10) = 4.905181
arrayOfVariantOfDouble332(11) = 0.000000
move4.Apply arrayOfVariantOfDouble332

Set move4 = product6.Move

Set move4 = move4.MovableObject

Dim arrayOfVariantOfDouble333(11)
arrayOfVariantOfDouble333(0) = 1.000000
arrayOfVariantOfDouble333(1) = 0.000000
arrayOfVariantOfDouble333(2) = 0.000000
arrayOfVariantOfDouble333(3) = 0.000000
arrayOfVariantOfDouble333(4) = 1.000000
arrayOfVariantOfDouble333(5) = 0.000000
arrayOfVariantOfDouble333(6) = 0.000000
arrayOfVariantOfDouble333(7) = 0.000000
arrayOfVariantOfDouble333(8) = 1.000000
arrayOfVariantOfDouble333(9) = 0.000000
arrayOfVariantOfDouble333(10) = 3.308795
arrayOfVariantOfDouble333(11) = 0.000000
move4.Apply arrayOfVariantOfDouble333

Set move4 = product6.Move

Set move4 = move4.MovableObject

Dim arrayOfVariantOfDouble334(11)
arrayOfVariantOfDouble334(0) = 1.000000
arrayOfVariantOfDouble334(1) = 0.000000
arrayOfVariantOfDouble334(2) = 0.000000
arrayOfVariantOfDouble334(3) = 0.000000
arrayOfVariantOfDouble334(4) = 1.000000
arrayOfVariantOfDouble334(5) = 0.000000
arrayOfVariantOfDouble334(6) = 0.000000
arrayOfVariantOfDouble334(7) = 0.000000
arrayOfVariantOfDouble334(8) = 1.000000
arrayOfVariantOfDouble334(9) = 0.000000
arrayOfVariantOfDouble334(10) = 3.250823
arrayOfVariantOfDouble334(11) = 0.000000
move4.Apply arrayOfVariantOfDouble334

Set move4 = product6.Move

Set move4 = move4.MovableObject

Dim arrayOfVariantOfDouble335(11)
arrayOfVariantOfDouble335(0) = 1.000000
arrayOfVariantOfDouble335(1) = 0.000000
arrayOfVariantOfDouble335(2) = 0.000000
arrayOfVariantOfDouble335(3) = 0.000000
arrayOfVariantOfDouble335(4) = 1.000000
arrayOfVariantOfDouble335(5) = 0.000000
arrayOfVariantOfDouble335(6) = 0.000000
arrayOfVariantOfDouble335(7) = 0.000000
arrayOfVariantOfDouble335(8) = 1.000000
arrayOfVariantOfDouble335(9) = 0.000000
arrayOfVariantOfDouble335(10) = 3.308753
arrayOfVariantOfDouble335(11) = 0.000000
move4.Apply arrayOfVariantOfDouble335

Set move4 = product6.Move

Set move4 = move4.MovableObject

Dim arrayOfVariantOfDouble336(11)
arrayOfVariantOfDouble336(0) = 1.000000
arrayOfVariantOfDouble336(1) = 0.000000
arrayOfVariantOfDouble336(2) = 0.000000
arrayOfVariantOfDouble336(3) = 0.000000
arrayOfVariantOfDouble336(4) = 1.000000
arrayOfVariantOfDouble336(5) = 0.000000
arrayOfVariantOfDouble336(6) = 0.000000
arrayOfVariantOfDouble336(7) = 0.000000
arrayOfVariantOfDouble336(8) = 1.000000
arrayOfVariantOfDouble336(9) = 0.000000
arrayOfVariantOfDouble336(10) = 0.798195
arrayOfVariantOfDouble336(11) = 0.000000
move4.Apply arrayOfVariantOfDouble336

Set move4 = product6.Move

Set move4 = move4.MovableObject

Dim arrayOfVariantOfDouble337(11)
arrayOfVariantOfDouble337(0) = 1.000000
arrayOfVariantOfDouble337(1) = 0.000000
arrayOfVariantOfDouble337(2) = 0.000000
arrayOfVariantOfDouble337(3) = 0.000000
arrayOfVariantOfDouble337(4) = 1.000000
arrayOfVariantOfDouble337(5) = 0.000000
arrayOfVariantOfDouble337(6) = 0.000000
arrayOfVariantOfDouble337(7) = 0.000000
arrayOfVariantOfDouble337(8) = 1.000000
arrayOfVariantOfDouble337(9) = 0.000000
arrayOfVariantOfDouble337(10) = 2.452625
arrayOfVariantOfDouble337(11) = 0.000000
move4.Apply arrayOfVariantOfDouble337

Set move4 = product6.Move

Set move4 = move4.MovableObject

Dim arrayOfVariantOfDouble338(11)
arrayOfVariantOfDouble338(0) = 1.000000
arrayOfVariantOfDouble338(1) = 0.000000
arrayOfVariantOfDouble338(2) = 0.000000
arrayOfVariantOfDouble338(3) = 0.000000
arrayOfVariantOfDouble338(4) = 1.000000
arrayOfVariantOfDouble338(5) = 0.000000
arrayOfVariantOfDouble338(6) = 0.000000
arrayOfVariantOfDouble338(7) = 0.000000
arrayOfVariantOfDouble338(8) = 1.000000
arrayOfVariantOfDouble338(9) = 0.000000
arrayOfVariantOfDouble338(10) = 1.654361
arrayOfVariantOfDouble338(11) = 0.000000
move4.Apply arrayOfVariantOfDouble338

Set move4 = product6.Move

Set move4 = move4.MovableObject

Dim arrayOfVariantOfDouble339(11)
arrayOfVariantOfDouble339(0) = 1.000000
arrayOfVariantOfDouble339(1) = 0.000000
arrayOfVariantOfDouble339(2) = 0.000000
arrayOfVariantOfDouble339(3) = 0.000000
arrayOfVariantOfDouble339(4) = 1.000000
arrayOfVariantOfDouble339(5) = 0.000000
arrayOfVariantOfDouble339(6) = 0.000000
arrayOfVariantOfDouble339(7) = 0.000000
arrayOfVariantOfDouble339(8) = 1.000000
arrayOfVariantOfDouble339(9) = 0.000000
arrayOfVariantOfDouble339(10) = 0.798231
arrayOfVariantOfDouble339(11) = 0.000000
move4.Apply arrayOfVariantOfDouble339

Set move4 = product6.Move

Set move4 = move4.MovableObject

Dim arrayOfVariantOfDouble340(11)
arrayOfVariantOfDouble340(0) = 1.000000
arrayOfVariantOfDouble340(1) = 0.000000
arrayOfVariantOfDouble340(2) = 0.000000
arrayOfVariantOfDouble340(3) = 0.000000
arrayOfVariantOfDouble340(4) = 1.000000
arrayOfVariantOfDouble340(5) = 0.000000
arrayOfVariantOfDouble340(6) = 0.000000
arrayOfVariantOfDouble340(7) = 0.000000
arrayOfVariantOfDouble340(8) = 1.000000
arrayOfVariantOfDouble340(9) = 0.000000
arrayOfVariantOfDouble340(10) = 0.798194
arrayOfVariantOfDouble340(11) = 0.000000
move4.Apply arrayOfVariantOfDouble340

Set move4 = product6.Move

Set move4 = move4.MovableObject

Dim arrayOfVariantOfDouble341(11)
arrayOfVariantOfDouble341(0) = 1.000000
arrayOfVariantOfDouble341(1) = 0.000000
arrayOfVariantOfDouble341(2) = 0.000000
arrayOfVariantOfDouble341(3) = 0.000000
arrayOfVariantOfDouble341(4) = 1.000000
arrayOfVariantOfDouble341(5) = 0.000000
arrayOfVariantOfDouble341(6) = 0.000000
arrayOfVariantOfDouble341(7) = 0.000000
arrayOfVariantOfDouble341(8) = 1.000000
arrayOfVariantOfDouble341(9) = 0.000000
arrayOfVariantOfDouble341(10) = 0.856161
arrayOfVariantOfDouble341(11) = 0.000000
move4.Apply arrayOfVariantOfDouble341

Set move4 = product6.Move

Set move4 = move4.MovableObject

Dim arrayOfVariantOfDouble342(11)
arrayOfVariantOfDouble342(0) = 1.000000
arrayOfVariantOfDouble342(1) = 0.000000
arrayOfVariantOfDouble342(2) = 0.000000
arrayOfVariantOfDouble342(3) = 0.000000
arrayOfVariantOfDouble342(4) = 1.000000
arrayOfVariantOfDouble342(5) = 0.000000
arrayOfVariantOfDouble342(6) = 0.000000
arrayOfVariantOfDouble342(7) = 0.000000
arrayOfVariantOfDouble342(8) = 1.000000
arrayOfVariantOfDouble342(9) = 0.000000
arrayOfVariantOfDouble342(10) = 0.798231
arrayOfVariantOfDouble342(11) = 0.000000
move4.Apply arrayOfVariantOfDouble342

Set move4 = product6.Move

Set move4 = move4.MovableObject

Dim arrayOfVariantOfDouble343(11)
arrayOfVariantOfDouble343(0) = 1.000000
arrayOfVariantOfDouble343(1) = 0.000000
arrayOfVariantOfDouble343(2) = 0.000000
arrayOfVariantOfDouble343(3) = 0.000000
arrayOfVariantOfDouble343(4) = 1.000000
arrayOfVariantOfDouble343(5) = 0.000000
arrayOfVariantOfDouble343(6) = 0.000000
arrayOfVariantOfDouble343(7) = 0.000000
arrayOfVariantOfDouble343(8) = 1.000000
arrayOfVariantOfDouble343(9) = 0.000000
arrayOfVariantOfDouble343(10) = 0.798229
arrayOfVariantOfDouble343(11) = 0.000000
move4.Apply arrayOfVariantOfDouble343

Set constraints1 = product1.Connections("CATIAConstraints")

Set reference7 = product1.CreateReferenceFromName("A2/DM.1/!Axis:(Selection_RSur:(Face:(Brp:(Pocket.2;0:(Brp:(Sketch.3;4)));None:();Cf11:());Pocket.2_ResultOUT;Z0;G4162))")

Dim reference44 As Reference
Set reference44 = product1.CreateReferenceFromName("A2/Bolt.4/!Axis:(Selection_RSur:(Face:(Brp:(Shaft.1;0:(Brp:(Sketch.1;10)));None:();Cf11:());Pad.1_ResultOUT;Z0;G4162))")

Dim constraint29 As Constraint
Set constraint29 = constraints1.AddBiEltCst(catCstTypeOn, reference7, reference44)

Set constraints1 = product1.Connections("CATIAConstraints")

Dim reference45 As Reference
Set reference45 = product1.CreateReferenceFromName("A2/DM.1/!Selection_RSur:(Face:(Brp:(Pad.1;0:(Brp:(Sketch.1;8)));None:();Cf11:());Pocket.2_ResultOUT;Z0;G4162)")

Dim reference46 As Reference
Set reference46 = product1.CreateReferenceFromName("A2/Bolt.4/!Selection_RSur:(Face:(Brp:(Shaft.1;0:(Brp:(Sketch.1;8)));None:();Cf11:());Pad.1_ResultOUT;Z0;G4162)")

Dim constraint30 As Constraint
Set constraint30 = constraints1.AddBiEltCst(catCstTypeSurfContact, reference45, reference46)

product1.Update 

Set constraints1 = product1.Connections("CATIAConstraints")

Dim reference47 As Reference
Set reference47 = product1.CreateReferenceFromName("A2/Bolt.4/!Selection_REdge:(Edge:(Face:(Brp:(Pad.1;0:(Brp:(Sketch.2;10)));None:();Cf11:());Face:(Brp:(Pad.1;2);None:();Cf11:());None:(Limits1:();Limits2:());Cf11:());Pad.1_ResultOUT;Z0;G4162)")

Dim reference48 As Reference
Set reference48 = product1.CreateReferenceFromName("A2/Plate.1/!Selection_REdge:(Edge:(Face:(Brp:(Pad.1;1);None:();Cf11:());Face:(Brp:(Pad.1;0:(Brp:(Sketch.1;6)));None:();Cf11:());None:(Limits1:();Limits2:());Cf11:());Pad.1_ResultOUT;Z0;G4162)")

Dim constraint31 As Constraint
Set constraint31 = constraints1.AddBiEltCst(catCstTypeAngle, reference47, reference48)

Dim angle6 As Dimension
Set angle6 = constraint31.Dimension

angle6.Value = 0.000000

product1.Update 

Dim arrayOfVariantOfBSTR12(0)
arrayOfVariantOfBSTR12(0) = ".\SubAssembly\Bolt.CATPart"
products1.AddComponentsFromFiles arrayOfVariantOfBSTR12, "All"

Dim product7 As Product
Set product7 = products1.Item("Bolt.5")

Dim move5 As Move
Set move5 = product7.Move

Set move5 = move5.MovableObject

Dim arrayOfVariantOfDouble344(11)
arrayOfVariantOfDouble344(0) = 1.000000
arrayOfVariantOfDouble344(1) = 0.000000
arrayOfVariantOfDouble344(2) = 0.000000
arrayOfVariantOfDouble344(3) = 0.000000
arrayOfVariantOfDouble344(4) = 1.000000
arrayOfVariantOfDouble344(5) = 0.000000
arrayOfVariantOfDouble344(6) = 0.000000
arrayOfVariantOfDouble344(7) = 0.000000
arrayOfVariantOfDouble344(8) = 1.000000
arrayOfVariantOfDouble344(9) = 0.000000
arrayOfVariantOfDouble344(10) = -0.577316
arrayOfVariantOfDouble344(11) = 0.000000
move5.Apply arrayOfVariantOfDouble344

Set move5 = product7.Move

Set move5 = move5.MovableObject

Dim arrayOfVariantOfDouble345(11)
arrayOfVariantOfDouble345(0) = 1.000000
arrayOfVariantOfDouble345(1) = 0.000000
arrayOfVariantOfDouble345(2) = 0.000000
arrayOfVariantOfDouble345(3) = 0.000000
arrayOfVariantOfDouble345(4) = 1.000000
arrayOfVariantOfDouble345(5) = 0.000000
arrayOfVariantOfDouble345(6) = 0.000000
arrayOfVariantOfDouble345(7) = 0.000000
arrayOfVariantOfDouble345(8) = 1.000000
arrayOfVariantOfDouble345(9) = 0.000000
arrayOfVariantOfDouble345(10) = 2.789748
arrayOfVariantOfDouble345(11) = 0.000000
move5.Apply arrayOfVariantOfDouble345

Set move5 = product7.Move

Set move5 = move5.MovableObject

Dim arrayOfVariantOfDouble346(11)
arrayOfVariantOfDouble346(0) = 1.000000
arrayOfVariantOfDouble346(1) = 0.000000
arrayOfVariantOfDouble346(2) = 0.000000
arrayOfVariantOfDouble346(3) = 0.000000
arrayOfVariantOfDouble346(4) = 1.000000
arrayOfVariantOfDouble346(5) = 0.000000
arrayOfVariantOfDouble346(6) = 0.000000
arrayOfVariantOfDouble346(7) = 0.000000
arrayOfVariantOfDouble346(8) = 1.000000
arrayOfVariantOfDouble346(9) = 0.000000
arrayOfVariantOfDouble346(10) = 1.844904
arrayOfVariantOfDouble346(11) = 0.000000
move5.Apply arrayOfVariantOfDouble346

Set move5 = product7.Move

Set move5 = move5.MovableObject

Dim arrayOfVariantOfDouble347(11)
arrayOfVariantOfDouble347(0) = 1.000000
arrayOfVariantOfDouble347(1) = 0.000000
arrayOfVariantOfDouble347(2) = 0.000000
arrayOfVariantOfDouble347(3) = 0.000000
arrayOfVariantOfDouble347(4) = 1.000000
arrayOfVariantOfDouble347(5) = 0.000000
arrayOfVariantOfDouble347(6) = 0.000000
arrayOfVariantOfDouble347(7) = 0.000000
arrayOfVariantOfDouble347(8) = 1.000000
arrayOfVariantOfDouble347(9) = 0.000000
arrayOfVariantOfDouble347(10) = 3.734604
arrayOfVariantOfDouble347(11) = 0.000000
move5.Apply arrayOfVariantOfDouble347

Set move5 = product7.Move

Set move5 = move5.MovableObject

Dim arrayOfVariantOfDouble348(11)
arrayOfVariantOfDouble348(0) = 1.000000
arrayOfVariantOfDouble348(1) = 0.000000
arrayOfVariantOfDouble348(2) = 0.000000
arrayOfVariantOfDouble348(3) = 0.000000
arrayOfVariantOfDouble348(4) = 1.000000
arrayOfVariantOfDouble348(5) = 0.000000
arrayOfVariantOfDouble348(6) = 0.000000
arrayOfVariantOfDouble348(7) = 0.000000
arrayOfVariantOfDouble348(8) = 1.000000
arrayOfVariantOfDouble348(9) = 0.000000
arrayOfVariantOfDouble348(10) = 3.734610
arrayOfVariantOfDouble348(11) = 0.000000
move5.Apply arrayOfVariantOfDouble348

Set move5 = product7.Move

Set move5 = move5.MovableObject

Dim arrayOfVariantOfDouble349(11)
arrayOfVariantOfDouble349(0) = 1.000000
arrayOfVariantOfDouble349(1) = 0.000000
arrayOfVariantOfDouble349(2) = 0.000000
arrayOfVariantOfDouble349(3) = 0.000000
arrayOfVariantOfDouble349(4) = 1.000000
arrayOfVariantOfDouble349(5) = 0.000000
arrayOfVariantOfDouble349(6) = 0.000000
arrayOfVariantOfDouble349(7) = 0.000000
arrayOfVariantOfDouble349(8) = 1.000000
arrayOfVariantOfDouble349(9) = 0.000000
arrayOfVariantOfDouble349(10) = 4.184636
arrayOfVariantOfDouble349(11) = 0.000000
move5.Apply arrayOfVariantOfDouble349

Set move5 = product7.Move

Set move5 = move5.MovableObject

Dim arrayOfVariantOfDouble350(11)
arrayOfVariantOfDouble350(0) = 1.000000
arrayOfVariantOfDouble350(1) = 0.000000
arrayOfVariantOfDouble350(2) = 0.000000
arrayOfVariantOfDouble350(3) = 0.000000
arrayOfVariantOfDouble350(4) = 1.000000
arrayOfVariantOfDouble350(5) = 0.000000
arrayOfVariantOfDouble350(6) = 0.000000
arrayOfVariantOfDouble350(7) = 0.000000
arrayOfVariantOfDouble350(8) = 1.000000
arrayOfVariantOfDouble350(9) = 0.000000
arrayOfVariantOfDouble350(10) = 5.579502
arrayOfVariantOfDouble350(11) = 0.000000
move5.Apply arrayOfVariantOfDouble350

Set move5 = product7.Move

Set move5 = move5.MovableObject

Dim arrayOfVariantOfDouble351(11)
arrayOfVariantOfDouble351(0) = 1.000000
arrayOfVariantOfDouble351(1) = 0.000000
arrayOfVariantOfDouble351(2) = 0.000000
arrayOfVariantOfDouble351(3) = 0.000000
arrayOfVariantOfDouble351(4) = 1.000000
arrayOfVariantOfDouble351(5) = 0.000000
arrayOfVariantOfDouble351(6) = 0.000000
arrayOfVariantOfDouble351(7) = 0.000000
arrayOfVariantOfDouble351(8) = 1.000000
arrayOfVariantOfDouble351(9) = 0.000000
arrayOfVariantOfDouble351(10) = 5.084666
arrayOfVariantOfDouble351(11) = 0.000000
move5.Apply arrayOfVariantOfDouble351

Set move5 = product7.Move

Set move5 = move5.MovableObject

Dim arrayOfVariantOfDouble352(11)
arrayOfVariantOfDouble352(0) = 1.000000
arrayOfVariantOfDouble352(1) = 0.000000
arrayOfVariantOfDouble352(2) = 0.000000
arrayOfVariantOfDouble352(3) = 0.000000
arrayOfVariantOfDouble352(4) = 1.000000
arrayOfVariantOfDouble352(5) = 0.000000
arrayOfVariantOfDouble352(6) = 0.000000
arrayOfVariantOfDouble352(7) = 0.000000
arrayOfVariantOfDouble352(8) = 1.000000
arrayOfVariantOfDouble352(9) = 0.000000
arrayOfVariantOfDouble352(10) = 6.569180
arrayOfVariantOfDouble352(11) = 0.000000
move5.Apply arrayOfVariantOfDouble352

Set move5 = product7.Move

Set move5 = move5.MovableObject

Dim arrayOfVariantOfDouble353(11)
arrayOfVariantOfDouble353(0) = 1.000000
arrayOfVariantOfDouble353(1) = 0.000000
arrayOfVariantOfDouble353(2) = 0.000000
arrayOfVariantOfDouble353(3) = 0.000000
arrayOfVariantOfDouble353(4) = 1.000000
arrayOfVariantOfDouble353(5) = 0.000000
arrayOfVariantOfDouble353(6) = 0.000000
arrayOfVariantOfDouble353(7) = 0.000000
arrayOfVariantOfDouble353(8) = 1.000000
arrayOfVariantOfDouble353(9) = 0.000000
arrayOfVariantOfDouble353(10) = 8.369259
arrayOfVariantOfDouble353(11) = 0.000000
move5.Apply arrayOfVariantOfDouble353

Set move5 = product7.Move

Set move5 = move5.MovableObject

Dim arrayOfVariantOfDouble354(11)
arrayOfVariantOfDouble354(0) = 1.000000
arrayOfVariantOfDouble354(1) = 0.000000
arrayOfVariantOfDouble354(2) = 0.000000
arrayOfVariantOfDouble354(3) = 0.000000
arrayOfVariantOfDouble354(4) = 1.000000
arrayOfVariantOfDouble354(5) = 0.000000
arrayOfVariantOfDouble354(6) = 0.000000
arrayOfVariantOfDouble354(7) = 0.000000
arrayOfVariantOfDouble354(8) = 1.000000
arrayOfVariantOfDouble354(9) = 0.000000
arrayOfVariantOfDouble354(10) = 4.634645
arrayOfVariantOfDouble354(11) = 0.000000
move5.Apply arrayOfVariantOfDouble354

Set move5 = product7.Move

Set move5 = move5.MovableObject

Dim arrayOfVariantOfDouble355(11)
arrayOfVariantOfDouble355(0) = 1.000000
arrayOfVariantOfDouble355(1) = 0.000000
arrayOfVariantOfDouble355(2) = 0.000000
arrayOfVariantOfDouble355(3) = 0.000000
arrayOfVariantOfDouble355(4) = 1.000000
arrayOfVariantOfDouble355(5) = 0.000000
arrayOfVariantOfDouble355(6) = 0.000000
arrayOfVariantOfDouble355(7) = 0.000000
arrayOfVariantOfDouble355(8) = 1.000000
arrayOfVariantOfDouble355(9) = 0.000000
arrayOfVariantOfDouble355(10) = 7.964054
arrayOfVariantOfDouble355(11) = 0.000000
move5.Apply arrayOfVariantOfDouble355

Set move5 = product7.Move

Set move5 = move5.MovableObject

Dim arrayOfVariantOfDouble356(11)
arrayOfVariantOfDouble356(0) = 1.000000
arrayOfVariantOfDouble356(1) = 0.000000
arrayOfVariantOfDouble356(2) = 0.000000
arrayOfVariantOfDouble356(3) = 0.000000
arrayOfVariantOfDouble356(4) = 1.000000
arrayOfVariantOfDouble356(5) = 0.000000
arrayOfVariantOfDouble356(6) = 0.000000
arrayOfVariantOfDouble356(7) = 0.000000
arrayOfVariantOfDouble356(8) = 1.000000
arrayOfVariantOfDouble356(9) = 0.000000
arrayOfVariantOfDouble356(10) = 4.634652
arrayOfVariantOfDouble356(11) = 0.000000
move5.Apply arrayOfVariantOfDouble356

Set move5 = product7.Move

Set move5 = move5.MovableObject

Dim arrayOfVariantOfDouble357(11)
arrayOfVariantOfDouble357(0) = 1.000000
arrayOfVariantOfDouble357(1) = 0.000000
arrayOfVariantOfDouble357(2) = 0.000000
arrayOfVariantOfDouble357(3) = 0.000000
arrayOfVariantOfDouble357(4) = 1.000000
arrayOfVariantOfDouble357(5) = 0.000000
arrayOfVariantOfDouble357(6) = 0.000000
arrayOfVariantOfDouble357(7) = 0.000000
arrayOfVariantOfDouble357(8) = 1.000000
arrayOfVariantOfDouble357(9) = 0.000000
arrayOfVariantOfDouble357(10) = 6.524358
arrayOfVariantOfDouble357(11) = 0.000000
move5.Apply arrayOfVariantOfDouble357

Set move5 = product7.Move

Set move5 = move5.MovableObject

Dim arrayOfVariantOfDouble358(11)
arrayOfVariantOfDouble358(0) = 1.000000
arrayOfVariantOfDouble358(1) = 0.000000
arrayOfVariantOfDouble358(2) = 0.000000
arrayOfVariantOfDouble358(3) = 0.000000
arrayOfVariantOfDouble358(4) = 1.000000
arrayOfVariantOfDouble358(5) = 0.000000
arrayOfVariantOfDouble358(6) = 0.000000
arrayOfVariantOfDouble358(7) = 0.000000
arrayOfVariantOfDouble358(8) = 1.000000
arrayOfVariantOfDouble358(9) = 0.000000
arrayOfVariantOfDouble358(10) = 3.734609
arrayOfVariantOfDouble358(11) = 0.000000
move5.Apply arrayOfVariantOfDouble358

Set move5 = product7.Move

Set move5 = move5.MovableObject

Dim arrayOfVariantOfDouble359(11)
arrayOfVariantOfDouble359(0) = 1.000000
arrayOfVariantOfDouble359(1) = 0.000000
arrayOfVariantOfDouble359(2) = 0.000000
arrayOfVariantOfDouble359(3) = 0.000000
arrayOfVariantOfDouble359(4) = 1.000000
arrayOfVariantOfDouble359(5) = 0.000000
arrayOfVariantOfDouble359(6) = 0.000000
arrayOfVariantOfDouble359(7) = 0.000000
arrayOfVariantOfDouble359(8) = 1.000000
arrayOfVariantOfDouble359(9) = 0.000000
arrayOfVariantOfDouble359(10) = 5.579500
arrayOfVariantOfDouble359(11) = 0.000000
move5.Apply arrayOfVariantOfDouble359

Set move5 = product7.Move

Set move5 = move5.MovableObject

Dim arrayOfVariantOfDouble360(11)
arrayOfVariantOfDouble360(0) = 1.000000
arrayOfVariantOfDouble360(1) = 0.000000
arrayOfVariantOfDouble360(2) = 0.000000
arrayOfVariantOfDouble360(3) = 0.000000
arrayOfVariantOfDouble360(4) = 1.000000
arrayOfVariantOfDouble360(5) = 0.000000
arrayOfVariantOfDouble360(6) = 0.000000
arrayOfVariantOfDouble360(7) = 0.000000
arrayOfVariantOfDouble360(8) = 1.000000
arrayOfVariantOfDouble360(9) = 0.000000
arrayOfVariantOfDouble360(10) = 4.634647
arrayOfVariantOfDouble360(11) = 0.000000
move5.Apply arrayOfVariantOfDouble360

Set move5 = product7.Move

Set move5 = move5.MovableObject

Dim arrayOfVariantOfDouble361(11)
arrayOfVariantOfDouble361(0) = 1.000000
arrayOfVariantOfDouble361(1) = 0.000000
arrayOfVariantOfDouble361(2) = 0.000000
arrayOfVariantOfDouble361(3) = 0.000000
arrayOfVariantOfDouble361(4) = 1.000000
arrayOfVariantOfDouble361(5) = 0.000000
arrayOfVariantOfDouble361(6) = 0.000000
arrayOfVariantOfDouble361(7) = 0.000000
arrayOfVariantOfDouble361(8) = 1.000000
arrayOfVariantOfDouble361(9) = 0.000000
arrayOfVariantOfDouble361(10) = 7.469219
arrayOfVariantOfDouble361(11) = 0.000000
move5.Apply arrayOfVariantOfDouble361

Set move5 = product7.Move

Set move5 = move5.MovableObject

Dim arrayOfVariantOfDouble362(11)
arrayOfVariantOfDouble362(0) = 1.000000
arrayOfVariantOfDouble362(1) = 0.000000
arrayOfVariantOfDouble362(2) = 0.000000
arrayOfVariantOfDouble362(3) = 0.000000
arrayOfVariantOfDouble362(4) = 1.000000
arrayOfVariantOfDouble362(5) = 0.000000
arrayOfVariantOfDouble362(6) = 0.000000
arrayOfVariantOfDouble362(7) = 0.000000
arrayOfVariantOfDouble362(8) = 1.000000
arrayOfVariantOfDouble362(9) = 0.000000
arrayOfVariantOfDouble362(10) = 5.129492
arrayOfVariantOfDouble362(11) = 0.000000
move5.Apply arrayOfVariantOfDouble362

Set move5 = product7.Move

Set move5 = move5.MovableObject

Dim arrayOfVariantOfDouble363(11)
arrayOfVariantOfDouble363(0) = 1.000000
arrayOfVariantOfDouble363(1) = 0.000000
arrayOfVariantOfDouble363(2) = 0.000000
arrayOfVariantOfDouble363(3) = 0.000000
arrayOfVariantOfDouble363(4) = 1.000000
arrayOfVariantOfDouble363(5) = 0.000000
arrayOfVariantOfDouble363(6) = 0.000000
arrayOfVariantOfDouble363(7) = 0.000000
arrayOfVariantOfDouble363(8) = 1.000000
arrayOfVariantOfDouble363(9) = 0.000000
arrayOfVariantOfDouble363(10) = 7.019194
arrayOfVariantOfDouble363(11) = 0.000000
move5.Apply arrayOfVariantOfDouble363

Set move5 = product7.Move

Set move5 = move5.MovableObject

Dim arrayOfVariantOfDouble364(11)
arrayOfVariantOfDouble364(0) = 1.000000
arrayOfVariantOfDouble364(1) = 0.000000
arrayOfVariantOfDouble364(2) = 0.000000
arrayOfVariantOfDouble364(3) = 0.000000
arrayOfVariantOfDouble364(4) = 1.000000
arrayOfVariantOfDouble364(5) = 0.000000
arrayOfVariantOfDouble364(6) = 0.000000
arrayOfVariantOfDouble364(7) = 0.000000
arrayOfVariantOfDouble364(8) = 1.000000
arrayOfVariantOfDouble364(9) = 0.000000
arrayOfVariantOfDouble364(10) = 4.184630
arrayOfVariantOfDouble364(11) = 0.000000
move5.Apply arrayOfVariantOfDouble364

Set move5 = product7.Move

Set move5 = move5.MovableObject

Dim arrayOfVariantOfDouble365(11)
arrayOfVariantOfDouble365(0) = 1.000000
arrayOfVariantOfDouble365(1) = 0.000000
arrayOfVariantOfDouble365(2) = 0.000000
arrayOfVariantOfDouble365(3) = 0.000000
arrayOfVariantOfDouble365(4) = 1.000000
arrayOfVariantOfDouble365(5) = 0.000000
arrayOfVariantOfDouble365(6) = 0.000000
arrayOfVariantOfDouble365(7) = 0.000000
arrayOfVariantOfDouble365(8) = 1.000000
arrayOfVariantOfDouble365(9) = 0.000000
arrayOfVariantOfDouble365(10) = 6.074347
arrayOfVariantOfDouble365(11) = 0.000000
move5.Apply arrayOfVariantOfDouble365

Set move5 = product7.Move

Set move5 = move5.MovableObject

Dim arrayOfVariantOfDouble366(11)
arrayOfVariantOfDouble366(0) = 1.000000
arrayOfVariantOfDouble366(1) = 0.000000
arrayOfVariantOfDouble366(2) = 0.000000
arrayOfVariantOfDouble366(3) = 0.000000
arrayOfVariantOfDouble366(4) = 1.000000
arrayOfVariantOfDouble366(5) = 0.000000
arrayOfVariantOfDouble366(6) = 0.000000
arrayOfVariantOfDouble366(7) = 0.000000
arrayOfVariantOfDouble366(8) = 1.000000
arrayOfVariantOfDouble366(9) = 0.000000
arrayOfVariantOfDouble366(10) = 4.229427
arrayOfVariantOfDouble366(11) = 0.000000
move5.Apply arrayOfVariantOfDouble366

Set move5 = product7.Move

Set move5 = move5.MovableObject

Dim arrayOfVariantOfDouble367(11)
arrayOfVariantOfDouble367(0) = 1.000000
arrayOfVariantOfDouble367(1) = 0.000000
arrayOfVariantOfDouble367(2) = 0.000000
arrayOfVariantOfDouble367(3) = 0.000000
arrayOfVariantOfDouble367(4) = 1.000000
arrayOfVariantOfDouble367(5) = 0.000000
arrayOfVariantOfDouble367(6) = 0.000000
arrayOfVariantOfDouble367(7) = 0.000000
arrayOfVariantOfDouble367(8) = 1.000000
arrayOfVariantOfDouble367(9) = 0.000000
arrayOfVariantOfDouble367(10) = 4.679477
arrayOfVariantOfDouble367(11) = 0.000000
move5.Apply arrayOfVariantOfDouble367

Set move5 = product7.Move

Set move5 = move5.MovableObject

Dim arrayOfVariantOfDouble368(11)
arrayOfVariantOfDouble368(0) = 1.000000
arrayOfVariantOfDouble368(1) = 0.000000
arrayOfVariantOfDouble368(2) = 0.000000
arrayOfVariantOfDouble368(3) = 0.000000
arrayOfVariantOfDouble368(4) = 1.000000
arrayOfVariantOfDouble368(5) = 0.000000
arrayOfVariantOfDouble368(6) = 0.000000
arrayOfVariantOfDouble368(7) = 0.000000
arrayOfVariantOfDouble368(8) = 1.000000
arrayOfVariantOfDouble368(9) = 0.000000
arrayOfVariantOfDouble368(10) = 6.569177
arrayOfVariantOfDouble368(11) = 0.000000
move5.Apply arrayOfVariantOfDouble368

Set move5 = product7.Move

Set move5 = move5.MovableObject

Dim arrayOfVariantOfDouble369(11)
arrayOfVariantOfDouble369(0) = 1.000000
arrayOfVariantOfDouble369(1) = 0.000000
arrayOfVariantOfDouble369(2) = 0.000000
arrayOfVariantOfDouble369(3) = 0.000000
arrayOfVariantOfDouble369(4) = 1.000000
arrayOfVariantOfDouble369(5) = 0.000000
arrayOfVariantOfDouble369(6) = 0.000000
arrayOfVariantOfDouble369(7) = 0.000000
arrayOfVariantOfDouble369(8) = 1.000000
arrayOfVariantOfDouble369(9) = 0.000000
arrayOfVariantOfDouble369(10) = 4.184618
arrayOfVariantOfDouble369(11) = 0.000000
move5.Apply arrayOfVariantOfDouble369

Set move5 = product7.Move

Set move5 = move5.MovableObject

Dim arrayOfVariantOfDouble370(11)
arrayOfVariantOfDouble370(0) = 1.000000
arrayOfVariantOfDouble370(1) = 0.000000
arrayOfVariantOfDouble370(2) = 0.000000
arrayOfVariantOfDouble370(3) = 0.000000
arrayOfVariantOfDouble370(4) = 1.000000
arrayOfVariantOfDouble370(5) = 0.000000
arrayOfVariantOfDouble370(6) = 0.000000
arrayOfVariantOfDouble370(7) = 0.000000
arrayOfVariantOfDouble370(8) = 1.000000
arrayOfVariantOfDouble370(9) = 0.000000
arrayOfVariantOfDouble370(10) = 6.074361
arrayOfVariantOfDouble370(11) = 0.000000
move5.Apply arrayOfVariantOfDouble370

Set move5 = product7.Move

Set move5 = move5.MovableObject

Dim arrayOfVariantOfDouble371(11)
arrayOfVariantOfDouble371(0) = 1.000000
arrayOfVariantOfDouble371(1) = 0.000000
arrayOfVariantOfDouble371(2) = 0.000000
arrayOfVariantOfDouble371(3) = 0.000000
arrayOfVariantOfDouble371(4) = 1.000000
arrayOfVariantOfDouble371(5) = 0.000000
arrayOfVariantOfDouble371(6) = 0.000000
arrayOfVariantOfDouble371(7) = 0.000000
arrayOfVariantOfDouble371(8) = 1.000000
arrayOfVariantOfDouble371(9) = 0.000000
arrayOfVariantOfDouble371(10) = 6.074326
arrayOfVariantOfDouble371(11) = 0.000000
move5.Apply arrayOfVariantOfDouble371

Set move5 = product7.Move

Set move5 = move5.MovableObject

Dim arrayOfVariantOfDouble372(11)
arrayOfVariantOfDouble372(0) = 1.000000
arrayOfVariantOfDouble372(1) = 0.000000
arrayOfVariantOfDouble372(2) = 0.000000
arrayOfVariantOfDouble372(3) = 0.000000
arrayOfVariantOfDouble372(4) = 1.000000
arrayOfVariantOfDouble372(5) = 0.000000
arrayOfVariantOfDouble372(6) = 0.000000
arrayOfVariantOfDouble372(7) = 0.000000
arrayOfVariantOfDouble372(8) = 1.000000
arrayOfVariantOfDouble372(9) = 0.000000
arrayOfVariantOfDouble372(10) = 5.084681
arrayOfVariantOfDouble372(11) = 0.000000
move5.Apply arrayOfVariantOfDouble372

Set move5 = product7.Move

Set move5 = move5.MovableObject

Dim arrayOfVariantOfDouble373(11)
arrayOfVariantOfDouble373(0) = 1.000000
arrayOfVariantOfDouble373(1) = 0.000000
arrayOfVariantOfDouble373(2) = 0.000000
arrayOfVariantOfDouble373(3) = 0.000000
arrayOfVariantOfDouble373(4) = 1.000000
arrayOfVariantOfDouble373(5) = 0.000000
arrayOfVariantOfDouble373(6) = 0.000000
arrayOfVariantOfDouble373(7) = 0.000000
arrayOfVariantOfDouble373(8) = 1.000000
arrayOfVariantOfDouble373(9) = 0.000000
arrayOfVariantOfDouble373(10) = 5.129464
arrayOfVariantOfDouble373(11) = 0.000000
move5.Apply arrayOfVariantOfDouble373

Set move5 = product7.Move

Set move5 = move5.MovableObject

Dim arrayOfVariantOfDouble374(11)
arrayOfVariantOfDouble374(0) = 1.000000
arrayOfVariantOfDouble374(1) = 0.000000
arrayOfVariantOfDouble374(2) = 0.000000
arrayOfVariantOfDouble374(3) = 0.000000
arrayOfVariantOfDouble374(4) = 1.000000
arrayOfVariantOfDouble374(5) = 0.000000
arrayOfVariantOfDouble374(6) = 0.000000
arrayOfVariantOfDouble374(7) = 0.000000
arrayOfVariantOfDouble374(8) = 1.000000
arrayOfVariantOfDouble374(9) = 0.000000
arrayOfVariantOfDouble374(10) = 8.414073
arrayOfVariantOfDouble374(11) = 0.000000
move5.Apply arrayOfVariantOfDouble374

Set move5 = product7.Move

Set move5 = move5.MovableObject

Dim arrayOfVariantOfDouble375(11)
arrayOfVariantOfDouble375(0) = 1.000000
arrayOfVariantOfDouble375(1) = 0.000000
arrayOfVariantOfDouble375(2) = 0.000000
arrayOfVariantOfDouble375(3) = 0.000000
arrayOfVariantOfDouble375(4) = 1.000000
arrayOfVariantOfDouble375(5) = 0.000000
arrayOfVariantOfDouble375(6) = 0.000000
arrayOfVariantOfDouble375(7) = 0.000000
arrayOfVariantOfDouble375(8) = 1.000000
arrayOfVariantOfDouble375(9) = 0.000000
arrayOfVariantOfDouble375(10) = 6.974398
arrayOfVariantOfDouble375(11) = 0.000000
move5.Apply arrayOfVariantOfDouble375

Set move5 = product7.Move

Set move5 = move5.MovableObject

Dim arrayOfVariantOfDouble376(11)
arrayOfVariantOfDouble376(0) = 1.000000
arrayOfVariantOfDouble376(1) = 0.000000
arrayOfVariantOfDouble376(2) = 0.000000
arrayOfVariantOfDouble376(3) = 0.000000
arrayOfVariantOfDouble376(4) = 1.000000
arrayOfVariantOfDouble376(5) = 0.000000
arrayOfVariantOfDouble376(6) = 0.000000
arrayOfVariantOfDouble376(7) = 0.000000
arrayOfVariantOfDouble376(8) = 1.000000
arrayOfVariantOfDouble376(9) = 0.000000
arrayOfVariantOfDouble376(10) = 6.524356
arrayOfVariantOfDouble376(11) = 0.000000
move5.Apply arrayOfVariantOfDouble376

Set move5 = product7.Move

Set move5 = move5.MovableObject

Dim arrayOfVariantOfDouble377(11)
arrayOfVariantOfDouble377(0) = 1.000000
arrayOfVariantOfDouble377(1) = 0.000000
arrayOfVariantOfDouble377(2) = 0.000000
arrayOfVariantOfDouble377(3) = 0.000000
arrayOfVariantOfDouble377(4) = 1.000000
arrayOfVariantOfDouble377(5) = 0.000000
arrayOfVariantOfDouble377(6) = 0.000000
arrayOfVariantOfDouble377(7) = 0.000000
arrayOfVariantOfDouble377(8) = 1.000000
arrayOfVariantOfDouble377(9) = 0.000000
arrayOfVariantOfDouble377(10) = 6.074331
arrayOfVariantOfDouble377(11) = 0.000000
move5.Apply arrayOfVariantOfDouble377

Set move5 = product7.Move

Set move5 = move5.MovableObject

Dim arrayOfVariantOfDouble378(11)
arrayOfVariantOfDouble378(0) = 1.000000
arrayOfVariantOfDouble378(1) = 0.000000
arrayOfVariantOfDouble378(2) = 0.000000
arrayOfVariantOfDouble378(3) = 0.000000
arrayOfVariantOfDouble378(4) = 1.000000
arrayOfVariantOfDouble378(5) = 0.000000
arrayOfVariantOfDouble378(6) = 0.000000
arrayOfVariantOfDouble378(7) = 0.000000
arrayOfVariantOfDouble378(8) = 1.000000
arrayOfVariantOfDouble378(9) = 0.000000
arrayOfVariantOfDouble378(10) = 7.019207
arrayOfVariantOfDouble378(11) = 0.000000
move5.Apply arrayOfVariantOfDouble378

Set move5 = product7.Move

Set move5 = move5.MovableObject

Dim arrayOfVariantOfDouble379(11)
arrayOfVariantOfDouble379(0) = 1.000000
arrayOfVariantOfDouble379(1) = 0.000000
arrayOfVariantOfDouble379(2) = 0.000000
arrayOfVariantOfDouble379(3) = 0.000000
arrayOfVariantOfDouble379(4) = 1.000000
arrayOfVariantOfDouble379(5) = 0.000000
arrayOfVariantOfDouble379(6) = 0.000000
arrayOfVariantOfDouble379(7) = 0.000000
arrayOfVariantOfDouble379(8) = 1.000000
arrayOfVariantOfDouble379(9) = 0.000000
arrayOfVariantOfDouble379(10) = 6.524363
arrayOfVariantOfDouble379(11) = 0.000000
move5.Apply arrayOfVariantOfDouble379

Set move5 = product7.Move

Set move5 = move5.MovableObject

Dim arrayOfVariantOfDouble380(11)
arrayOfVariantOfDouble380(0) = 1.000000
arrayOfVariantOfDouble380(1) = 0.000000
arrayOfVariantOfDouble380(2) = 0.000000
arrayOfVariantOfDouble380(3) = 0.000000
arrayOfVariantOfDouble380(4) = 1.000000
arrayOfVariantOfDouble380(5) = 0.000000
arrayOfVariantOfDouble380(6) = 0.000000
arrayOfVariantOfDouble380(7) = 0.000000
arrayOfVariantOfDouble380(8) = 1.000000
arrayOfVariantOfDouble380(9) = 0.000000
arrayOfVariantOfDouble380(10) = 4.679461
arrayOfVariantOfDouble380(11) = 0.000000
move5.Apply arrayOfVariantOfDouble380

Set move5 = product7.Move

Set move5 = move5.MovableObject

Dim arrayOfVariantOfDouble381(11)
arrayOfVariantOfDouble381(0) = 1.000000
arrayOfVariantOfDouble381(1) = 0.000000
arrayOfVariantOfDouble381(2) = 0.000000
arrayOfVariantOfDouble381(3) = 0.000000
arrayOfVariantOfDouble381(4) = 1.000000
arrayOfVariantOfDouble381(5) = 0.000000
arrayOfVariantOfDouble381(6) = 0.000000
arrayOfVariantOfDouble381(7) = 0.000000
arrayOfVariantOfDouble381(8) = 1.000000
arrayOfVariantOfDouble381(9) = 0.000000
arrayOfVariantOfDouble381(10) = 7.424391
arrayOfVariantOfDouble381(11) = 0.000000
move5.Apply arrayOfVariantOfDouble381

Set move5 = product7.Move

Set move5 = move5.MovableObject

Dim arrayOfVariantOfDouble382(11)
arrayOfVariantOfDouble382(0) = 1.000000
arrayOfVariantOfDouble382(1) = 0.000000
arrayOfVariantOfDouble382(2) = 0.000000
arrayOfVariantOfDouble382(3) = 0.000000
arrayOfVariantOfDouble382(4) = 1.000000
arrayOfVariantOfDouble382(5) = 0.000000
arrayOfVariantOfDouble382(6) = 0.000000
arrayOfVariantOfDouble382(7) = 0.000000
arrayOfVariantOfDouble382(8) = 1.000000
arrayOfVariantOfDouble382(9) = 0.000000
arrayOfVariantOfDouble382(10) = 6.524362
arrayOfVariantOfDouble382(11) = 0.000000
move5.Apply arrayOfVariantOfDouble382

Set move5 = product7.Move

Set move5 = move5.MovableObject

Dim arrayOfVariantOfDouble383(11)
arrayOfVariantOfDouble383(0) = 1.000000
arrayOfVariantOfDouble383(1) = 0.000000
arrayOfVariantOfDouble383(2) = 0.000000
arrayOfVariantOfDouble383(3) = 0.000000
arrayOfVariantOfDouble383(4) = 1.000000
arrayOfVariantOfDouble383(5) = 0.000000
arrayOfVariantOfDouble383(6) = 0.000000
arrayOfVariantOfDouble383(7) = 0.000000
arrayOfVariantOfDouble383(8) = 1.000000
arrayOfVariantOfDouble383(9) = 0.000000
arrayOfVariantOfDouble383(10) = 3.239776
arrayOfVariantOfDouble383(11) = 0.000000
move5.Apply arrayOfVariantOfDouble383

Set move5 = product7.Move

Set move5 = move5.MovableObject

Dim arrayOfVariantOfDouble384(11)
arrayOfVariantOfDouble384(0) = 1.000000
arrayOfVariantOfDouble384(1) = 0.000000
arrayOfVariantOfDouble384(2) = 0.000000
arrayOfVariantOfDouble384(3) = 0.000000
arrayOfVariantOfDouble384(4) = 1.000000
arrayOfVariantOfDouble384(5) = 0.000000
arrayOfVariantOfDouble384(6) = 0.000000
arrayOfVariantOfDouble384(7) = 0.000000
arrayOfVariantOfDouble384(8) = 1.000000
arrayOfVariantOfDouble384(9) = 0.000000
arrayOfVariantOfDouble384(10) = 3.689801
arrayOfVariantOfDouble384(11) = 0.000000
move5.Apply arrayOfVariantOfDouble384

Set move5 = product7.Move

Set move5 = move5.MovableObject

Dim arrayOfVariantOfDouble385(11)
arrayOfVariantOfDouble385(0) = 1.000000
arrayOfVariantOfDouble385(1) = 0.000000
arrayOfVariantOfDouble385(2) = 0.000000
arrayOfVariantOfDouble385(3) = 0.000000
arrayOfVariantOfDouble385(4) = 1.000000
arrayOfVariantOfDouble385(5) = 0.000000
arrayOfVariantOfDouble385(6) = 0.000000
arrayOfVariantOfDouble385(7) = 0.000000
arrayOfVariantOfDouble385(8) = 1.000000
arrayOfVariantOfDouble385(9) = 0.000000
arrayOfVariantOfDouble385(10) = 1.844899
arrayOfVariantOfDouble385(11) = 0.000000
move5.Apply arrayOfVariantOfDouble385

Set move5 = product7.Move

Set move5 = move5.MovableObject

Dim arrayOfVariantOfDouble386(11)
arrayOfVariantOfDouble386(0) = 1.000000
arrayOfVariantOfDouble386(1) = 0.000000
arrayOfVariantOfDouble386(2) = 0.000000
arrayOfVariantOfDouble386(3) = 0.000000
arrayOfVariantOfDouble386(4) = 1.000000
arrayOfVariantOfDouble386(5) = 0.000000
arrayOfVariantOfDouble386(6) = 0.000000
arrayOfVariantOfDouble386(7) = 0.000000
arrayOfVariantOfDouble386(8) = 1.000000
arrayOfVariantOfDouble386(9) = 0.000000
arrayOfVariantOfDouble386(10) = 2.789746
arrayOfVariantOfDouble386(11) = 0.000000
move5.Apply arrayOfVariantOfDouble386

Set move5 = product7.Move

Set move5 = move5.MovableObject

Dim arrayOfVariantOfDouble387(11)
arrayOfVariantOfDouble387(0) = 1.000000
arrayOfVariantOfDouble387(1) = 0.000000
arrayOfVariantOfDouble387(2) = 0.000000
arrayOfVariantOfDouble387(3) = 0.000000
arrayOfVariantOfDouble387(4) = 1.000000
arrayOfVariantOfDouble387(5) = 0.000000
arrayOfVariantOfDouble387(6) = 0.000000
arrayOfVariantOfDouble387(7) = 0.000000
arrayOfVariantOfDouble387(8) = 1.000000
arrayOfVariantOfDouble387(9) = 0.000000
arrayOfVariantOfDouble387(10) = 1.844902
arrayOfVariantOfDouble387(11) = 0.000000
move5.Apply arrayOfVariantOfDouble387

Set move5 = product7.Move

Set move5 = move5.MovableObject

Dim arrayOfVariantOfDouble388(11)
arrayOfVariantOfDouble388(0) = 1.000000
arrayOfVariantOfDouble388(1) = 0.000000
arrayOfVariantOfDouble388(2) = 0.000000
arrayOfVariantOfDouble388(3) = 0.000000
arrayOfVariantOfDouble388(4) = 1.000000
arrayOfVariantOfDouble388(5) = 0.000000
arrayOfVariantOfDouble388(6) = 0.000000
arrayOfVariantOfDouble388(7) = 0.000000
arrayOfVariantOfDouble388(8) = 1.000000
arrayOfVariantOfDouble388(9) = 0.000000
arrayOfVariantOfDouble388(10) = 0.450029
arrayOfVariantOfDouble388(11) = 0.000000
move5.Apply arrayOfVariantOfDouble388

Set move5 = product7.Move

Set move5 = move5.MovableObject

Dim arrayOfVariantOfDouble389(11)
arrayOfVariantOfDouble389(0) = 1.000000
arrayOfVariantOfDouble389(1) = 0.000000
arrayOfVariantOfDouble389(2) = 0.000000
arrayOfVariantOfDouble389(3) = 0.000000
arrayOfVariantOfDouble389(4) = 1.000000
arrayOfVariantOfDouble389(5) = 0.000000
arrayOfVariantOfDouble389(6) = 0.000000
arrayOfVariantOfDouble389(7) = 0.000000
arrayOfVariantOfDouble389(8) = 1.000000
arrayOfVariantOfDouble389(9) = 0.000000
arrayOfVariantOfDouble389(10) = 0.944844
arrayOfVariantOfDouble389(11) = 0.000000
move5.Apply arrayOfVariantOfDouble389

Set move5 = product7.Move

Set move5 = move5.MovableObject

Dim arrayOfVariantOfDouble390(11)
arrayOfVariantOfDouble390(0) = 1.000000
arrayOfVariantOfDouble390(1) = 0.000000
arrayOfVariantOfDouble390(2) = 0.000000
arrayOfVariantOfDouble390(3) = 0.000000
arrayOfVariantOfDouble390(4) = 1.000000
arrayOfVariantOfDouble390(5) = 0.000000
arrayOfVariantOfDouble390(6) = 0.000000
arrayOfVariantOfDouble390(7) = 0.000000
arrayOfVariantOfDouble390(8) = 1.000000
arrayOfVariantOfDouble390(9) = 0.000000
arrayOfVariantOfDouble390(10) = 0.450026
arrayOfVariantOfDouble390(11) = 0.000000
move5.Apply arrayOfVariantOfDouble390

Set move5 = product7.Move

Set move5 = move5.MovableObject

Dim arrayOfVariantOfDouble391(11)
arrayOfVariantOfDouble391(0) = 1.000000
arrayOfVariantOfDouble391(1) = 0.000000
arrayOfVariantOfDouble391(2) = 0.000000
arrayOfVariantOfDouble391(3) = 0.000000
arrayOfVariantOfDouble391(4) = 1.000000
arrayOfVariantOfDouble391(5) = 0.000000
arrayOfVariantOfDouble391(6) = 0.000000
arrayOfVariantOfDouble391(7) = 0.000000
arrayOfVariantOfDouble391(8) = 1.000000
arrayOfVariantOfDouble391(9) = 0.000000
arrayOfVariantOfDouble391(10) = 1.439688
arrayOfVariantOfDouble391(11) = 0.000000
move5.Apply arrayOfVariantOfDouble391

Set move5 = product7.Move

Set move5 = move5.MovableObject

Dim arrayOfVariantOfDouble392(11)
arrayOfVariantOfDouble392(0) = 1.000000
arrayOfVariantOfDouble392(1) = 0.000000
arrayOfVariantOfDouble392(2) = 0.000000
arrayOfVariantOfDouble392(3) = 0.000000
arrayOfVariantOfDouble392(4) = 1.000000
arrayOfVariantOfDouble392(5) = 0.000000
arrayOfVariantOfDouble392(6) = 0.000000
arrayOfVariantOfDouble392(7) = 0.000000
arrayOfVariantOfDouble392(8) = 1.000000
arrayOfVariantOfDouble392(9) = 0.000000
arrayOfVariantOfDouble392(10) = 0.494842
arrayOfVariantOfDouble392(11) = 0.000000
move5.Apply arrayOfVariantOfDouble392

Set constraints1 = product1.Connections("CATIAConstraints")

Set reference5 = product1.CreateReferenceFromName("A2/DM.1/!Axis:(Selection_RSur:(Face:(Brp:(Pocket.2;0:(Brp:(Sketch.3;6)));None:();Cf11:());Pocket.2_ResultOUT;Z0;G4162))")

Dim reference49 As Reference
Set reference49 = product1.CreateReferenceFromName("A2/Bolt.5/!Axis:(Selection_RSur:(Face:(Brp:(Shaft.1;0:(Brp:(Sketch.1;10)));None:();Cf11:());Pad.1_ResultOUT;Z0;G4162))")

Dim constraint32 As Constraint
Set constraint32 = constraints1.AddBiEltCst(catCstTypeOn, reference5, reference49)

Set constraints1 = product1.Connections("CATIAConstraints")

Set reference45 = product1.CreateReferenceFromName("A2/DM.1/!Selection_RSur:(Face:(Brp:(Pad.1;0:(Brp:(Sketch.1;8)));None:();Cf11:());Pocket.2_ResultOUT;Z0;G4162)")

Dim reference50 As Reference
Set reference50 = product1.CreateReferenceFromName("A2/Bolt.5/!Selection_RSur:(Face:(Brp:(Shaft.1;0:(Brp:(Sketch.1;8)));None:();Cf11:());Pad.1_ResultOUT;Z0;G4162)")

Dim constraint33 As Constraint
Set constraint33 = constraints1.AddBiEltCst(catCstTypeSurfContact, reference45, reference50)

product1.Update 

Set constraints1 = product1.Connections("CATIAConstraints")

Dim reference51 As Reference
Set reference51 = product1.CreateReferenceFromName("A2/Bolt.5/!Selection_REdge:(Edge:(Face:(Brp:(Pad.1;0:(Brp:(Sketch.2;10)));None:();Cf11:());Face:(Brp:(Pad.1;2);None:();Cf11:());None:(Limits1:();Limits2:());Cf11:());Pad.1_ResultOUT;Z0;G4162)")

Set reference48 = product1.CreateReferenceFromName("A2/Plate.1/!Selection_REdge:(Edge:(Face:(Brp:(Pad.1;1);None:();Cf11:());Face:(Brp:(Pad.1;0:(Brp:(Sketch.1;6)));None:();Cf11:());None:(Limits1:();Limits2:());Cf11:());Pad.1_ResultOUT;Z0;G4162)")

Dim constraint34 As Constraint
Set constraint34 = constraints1.AddBiEltCst(catCstTypeAngle, reference51, reference48)

Dim angle7 As Dimension
Set angle7 = constraint34.Dimension

angle7.Value = 0.000000

Dim arrayOfVariantOfBSTR13(0)
arrayOfVariantOfBSTR13(0) = ".\SubAssembly\Bolt.CATPart"
products1.AddComponentsFromFiles arrayOfVariantOfBSTR13, "All"

Dim product8 As Product
Set product8 = products1.Item("Bolt.6")

Dim move6 As Move
Set move6 = product8.Move

Set move6 = move6.MovableObject

Dim arrayOfVariantOfDouble393(11)
arrayOfVariantOfDouble393(0) = 1.000000
arrayOfVariantOfDouble393(1) = 0.000000
arrayOfVariantOfDouble393(2) = 0.000000
arrayOfVariantOfDouble393(3) = 0.000000
arrayOfVariantOfDouble393(4) = 1.000000
arrayOfVariantOfDouble393(5) = 0.000000
arrayOfVariantOfDouble393(6) = 0.000000
arrayOfVariantOfDouble393(7) = 0.000000
arrayOfVariantOfDouble393(8) = 1.000000
arrayOfVariantOfDouble393(9) = 0.000000
arrayOfVariantOfDouble393(10) = 18.584414
arrayOfVariantOfDouble393(11) = 0.000000
move6.Apply arrayOfVariantOfDouble393

Set move6 = product8.Move

Set move6 = move6.MovableObject

Dim arrayOfVariantOfDouble394(11)
arrayOfVariantOfDouble394(0) = 1.000000
arrayOfVariantOfDouble394(1) = 0.000000
arrayOfVariantOfDouble394(2) = 0.000000
arrayOfVariantOfDouble394(3) = 0.000000
arrayOfVariantOfDouble394(4) = 1.000000
arrayOfVariantOfDouble394(5) = 0.000000
arrayOfVariantOfDouble394(6) = 0.000000
arrayOfVariantOfDouble394(7) = 0.000000
arrayOfVariantOfDouble394(8) = 1.000000
arrayOfVariantOfDouble394(9) = 0.000000
arrayOfVariantOfDouble394(10) = 9.925060
arrayOfVariantOfDouble394(11) = 0.000000
move6.Apply arrayOfVariantOfDouble394

Set move6 = product8.Move

Set move6 = move6.MovableObject

Dim arrayOfVariantOfDouble395(11)
arrayOfVariantOfDouble395(0) = 1.000000
arrayOfVariantOfDouble395(1) = 0.000000
arrayOfVariantOfDouble395(2) = 0.000000
arrayOfVariantOfDouble395(3) = 0.000000
arrayOfVariantOfDouble395(4) = 1.000000
arrayOfVariantOfDouble395(5) = 0.000000
arrayOfVariantOfDouble395(6) = 0.000000
arrayOfVariantOfDouble395(7) = 0.000000
arrayOfVariantOfDouble395(8) = 1.000000
arrayOfVariantOfDouble395(9) = 0.000000
arrayOfVariantOfDouble395(10) = 9.925044
arrayOfVariantOfDouble395(11) = 0.000000
move6.Apply arrayOfVariantOfDouble395

Set move6 = product8.Move

Set move6 = move6.MovableObject

Dim arrayOfVariantOfDouble396(11)
arrayOfVariantOfDouble396(0) = 1.000000
arrayOfVariantOfDouble396(1) = 0.000000
arrayOfVariantOfDouble396(2) = 0.000000
arrayOfVariantOfDouble396(3) = 0.000000
arrayOfVariantOfDouble396(4) = 1.000000
arrayOfVariantOfDouble396(5) = 0.000000
arrayOfVariantOfDouble396(6) = 0.000000
arrayOfVariantOfDouble396(7) = 0.000000
arrayOfVariantOfDouble396(8) = 1.000000
arrayOfVariantOfDouble396(9) = 0.000000
arrayOfVariantOfDouble396(10) = 9.925045
arrayOfVariantOfDouble396(11) = 0.000000
move6.Apply arrayOfVariantOfDouble396

Set move6 = product8.Move

Set move6 = move6.MovableObject

Dim arrayOfVariantOfDouble397(11)
arrayOfVariantOfDouble397(0) = 1.000000
arrayOfVariantOfDouble397(1) = 0.000000
arrayOfVariantOfDouble397(2) = 0.000000
arrayOfVariantOfDouble397(3) = 0.000000
arrayOfVariantOfDouble397(4) = 1.000000
arrayOfVariantOfDouble397(5) = 0.000000
arrayOfVariantOfDouble397(6) = 0.000000
arrayOfVariantOfDouble397(7) = 0.000000
arrayOfVariantOfDouble397(8) = 1.000000
arrayOfVariantOfDouble397(9) = 0.000000
arrayOfVariantOfDouble397(10) = 8.695427
arrayOfVariantOfDouble397(11) = 0.000000
move6.Apply arrayOfVariantOfDouble397

Set move6 = product8.Move

Set move6 = move6.MovableObject

Dim arrayOfVariantOfDouble398(11)
arrayOfVariantOfDouble398(0) = 1.000000
arrayOfVariantOfDouble398(1) = 0.000000
arrayOfVariantOfDouble398(2) = 0.000000
arrayOfVariantOfDouble398(3) = 0.000000
arrayOfVariantOfDouble398(4) = 1.000000
arrayOfVariantOfDouble398(5) = 0.000000
arrayOfVariantOfDouble398(6) = 0.000000
arrayOfVariantOfDouble398(7) = 0.000000
arrayOfVariantOfDouble398(8) = 1.000000
arrayOfVariantOfDouble398(9) = 0.000000
arrayOfVariantOfDouble398(10) = 7.465757
arrayOfVariantOfDouble398(11) = 0.000000
move6.Apply arrayOfVariantOfDouble398

Set move6 = product8.Move

Set move6 = move6.MovableObject

Dim arrayOfVariantOfDouble399(11)
arrayOfVariantOfDouble399(0) = 1.000000
arrayOfVariantOfDouble399(1) = 0.000000
arrayOfVariantOfDouble399(2) = 0.000000
arrayOfVariantOfDouble399(3) = 0.000000
arrayOfVariantOfDouble399(4) = 1.000000
arrayOfVariantOfDouble399(5) = 0.000000
arrayOfVariantOfDouble399(6) = 0.000000
arrayOfVariantOfDouble399(7) = 0.000000
arrayOfVariantOfDouble399(8) = 1.000000
arrayOfVariantOfDouble399(9) = 0.000000
arrayOfVariantOfDouble399(10) = 6.616701
arrayOfVariantOfDouble399(11) = 0.000000
move6.Apply arrayOfVariantOfDouble399

Set move6 = product8.Move

Set move6 = move6.MovableObject

Dim arrayOfVariantOfDouble400(11)
arrayOfVariantOfDouble400(0) = 1.000000
arrayOfVariantOfDouble400(1) = 0.000000
arrayOfVariantOfDouble400(2) = 0.000000
arrayOfVariantOfDouble400(3) = 0.000000
arrayOfVariantOfDouble400(4) = 1.000000
arrayOfVariantOfDouble400(5) = 0.000000
arrayOfVariantOfDouble400(6) = 0.000000
arrayOfVariantOfDouble400(7) = 0.000000
arrayOfVariantOfDouble400(8) = 1.000000
arrayOfVariantOfDouble400(9) = 0.000000
arrayOfVariantOfDouble400(10) = 10.774096
arrayOfVariantOfDouble400(11) = 0.000000
move6.Apply arrayOfVariantOfDouble400

Set move6 = product8.Move

Set move6 = move6.MovableObject

Dim arrayOfVariantOfDouble401(11)
arrayOfVariantOfDouble401(0) = 1.000000
arrayOfVariantOfDouble401(1) = 0.000000
arrayOfVariantOfDouble401(2) = 0.000000
arrayOfVariantOfDouble401(3) = 0.000000
arrayOfVariantOfDouble401(4) = 1.000000
arrayOfVariantOfDouble401(5) = 0.000000
arrayOfVariantOfDouble401(6) = 0.000000
arrayOfVariantOfDouble401(7) = 0.000000
arrayOfVariantOfDouble401(8) = 1.000000
arrayOfVariantOfDouble401(9) = 0.000000
arrayOfVariantOfDouble401(10) = 6.616702
arrayOfVariantOfDouble401(11) = 0.000000
move6.Apply arrayOfVariantOfDouble401

Set move6 = product8.Move

Set move6 = move6.MovableObject

Dim arrayOfVariantOfDouble402(11)
arrayOfVariantOfDouble402(0) = 1.000000
arrayOfVariantOfDouble402(1) = 0.000000
arrayOfVariantOfDouble402(2) = 0.000000
arrayOfVariantOfDouble402(3) = 0.000000
arrayOfVariantOfDouble402(4) = 1.000000
arrayOfVariantOfDouble402(5) = 0.000000
arrayOfVariantOfDouble402(6) = 0.000000
arrayOfVariantOfDouble402(7) = 0.000000
arrayOfVariantOfDouble402(8) = 1.000000
arrayOfVariantOfDouble402(9) = 0.000000
arrayOfVariantOfDouble402(10) = 8.695437
arrayOfVariantOfDouble402(11) = 0.000000
move6.Apply arrayOfVariantOfDouble402

Set move6 = product8.Move

Set move6 = move6.MovableObject

Dim arrayOfVariantOfDouble403(11)
arrayOfVariantOfDouble403(0) = 1.000000
arrayOfVariantOfDouble403(1) = 0.000000
arrayOfVariantOfDouble403(2) = 0.000000
arrayOfVariantOfDouble403(3) = 0.000000
arrayOfVariantOfDouble403(4) = 1.000000
arrayOfVariantOfDouble403(5) = 0.000000
arrayOfVariantOfDouble403(6) = 0.000000
arrayOfVariantOfDouble403(7) = 0.000000
arrayOfVariantOfDouble403(8) = 1.000000
arrayOfVariantOfDouble403(9) = 0.000000
arrayOfVariantOfDouble403(10) = 8.695392
arrayOfVariantOfDouble403(11) = 0.000000
move6.Apply arrayOfVariantOfDouble403

Set move6 = product8.Move

Set move6 = move6.MovableObject

Dim arrayOfVariantOfDouble404(11)
arrayOfVariantOfDouble404(0) = 1.000000
arrayOfVariantOfDouble404(1) = 0.000000
arrayOfVariantOfDouble404(2) = 0.000000
arrayOfVariantOfDouble404(3) = 0.000000
arrayOfVariantOfDouble404(4) = 1.000000
arrayOfVariantOfDouble404(5) = 0.000000
arrayOfVariantOfDouble404(6) = 0.000000
arrayOfVariantOfDouble404(7) = 0.000000
arrayOfVariantOfDouble404(8) = 1.000000
arrayOfVariantOfDouble404(9) = 0.000000
arrayOfVariantOfDouble404(10) = 8.695407
arrayOfVariantOfDouble404(11) = 0.000000
move6.Apply arrayOfVariantOfDouble404

Set move6 = product8.Move

Set move6 = move6.MovableObject

Dim arrayOfVariantOfDouble405(11)
arrayOfVariantOfDouble405(0) = 1.000000
arrayOfVariantOfDouble405(1) = 0.000000
arrayOfVariantOfDouble405(2) = 0.000000
arrayOfVariantOfDouble405(3) = 0.000000
arrayOfVariantOfDouble405(4) = 1.000000
arrayOfVariantOfDouble405(5) = 0.000000
arrayOfVariantOfDouble405(6) = 0.000000
arrayOfVariantOfDouble405(7) = 0.000000
arrayOfVariantOfDouble405(8) = 1.000000
arrayOfVariantOfDouble405(9) = 0.000000
arrayOfVariantOfDouble405(10) = 16.161178
arrayOfVariantOfDouble405(11) = 0.000000
move6.Apply arrayOfVariantOfDouble405

Set move6 = product8.Move

Set move6 = move6.MovableObject

Dim arrayOfVariantOfDouble406(11)
arrayOfVariantOfDouble406(0) = 1.000000
arrayOfVariantOfDouble406(1) = 0.000000
arrayOfVariantOfDouble406(2) = 0.000000
arrayOfVariantOfDouble406(3) = 0.000000
arrayOfVariantOfDouble406(4) = 1.000000
arrayOfVariantOfDouble406(5) = 0.000000
arrayOfVariantOfDouble406(6) = 0.000000
arrayOfVariantOfDouble406(7) = 0.000000
arrayOfVariantOfDouble406(8) = 1.000000
arrayOfVariantOfDouble406(9) = 0.000000
arrayOfVariantOfDouble406(10) = 13.233398
arrayOfVariantOfDouble406(11) = 0.000000
move6.Apply arrayOfVariantOfDouble406

Set move6 = product8.Move

Set move6 = move6.MovableObject

Dim arrayOfVariantOfDouble407(11)
arrayOfVariantOfDouble407(0) = 1.000000
arrayOfVariantOfDouble407(1) = 0.000000
arrayOfVariantOfDouble407(2) = 0.000000
arrayOfVariantOfDouble407(3) = 0.000000
arrayOfVariantOfDouble407(4) = 1.000000
arrayOfVariantOfDouble407(5) = 0.000000
arrayOfVariantOfDouble407(6) = 0.000000
arrayOfVariantOfDouble407(7) = 0.000000
arrayOfVariantOfDouble407(8) = 1.000000
arrayOfVariantOfDouble407(9) = 0.000000
arrayOfVariantOfDouble407(10) = 18.620458
arrayOfVariantOfDouble407(11) = 0.000000
move6.Apply arrayOfVariantOfDouble407

Set move6 = product8.Move

Set move6 = move6.MovableObject

Dim arrayOfVariantOfDouble408(11)
arrayOfVariantOfDouble408(0) = 1.000000
arrayOfVariantOfDouble408(1) = 0.000000
arrayOfVariantOfDouble408(2) = 0.000000
arrayOfVariantOfDouble408(3) = 0.000000
arrayOfVariantOfDouble408(4) = 1.000000
arrayOfVariantOfDouble408(5) = 0.000000
arrayOfVariantOfDouble408(6) = 0.000000
arrayOfVariantOfDouble408(7) = 0.000000
arrayOfVariantOfDouble408(8) = 1.000000
arrayOfVariantOfDouble408(9) = 0.000000
arrayOfVariantOfDouble408(10) = 8.695400
arrayOfVariantOfDouble408(11) = 0.000000
move6.Apply arrayOfVariantOfDouble408

Set move6 = product8.Move

Set move6 = move6.MovableObject

Dim arrayOfVariantOfDouble409(11)
arrayOfVariantOfDouble409(0) = 1.000000
arrayOfVariantOfDouble409(1) = 0.000000
arrayOfVariantOfDouble409(2) = 0.000000
arrayOfVariantOfDouble409(3) = 0.000000
arrayOfVariantOfDouble409(4) = 1.000000
arrayOfVariantOfDouble409(5) = 0.000000
arrayOfVariantOfDouble409(6) = 0.000000
arrayOfVariantOfDouble409(7) = 0.000000
arrayOfVariantOfDouble409(8) = 1.000000
arrayOfVariantOfDouble409(9) = 0.000000
arrayOfVariantOfDouble409(10) = 14.082461
arrayOfVariantOfDouble409(11) = 0.000000
move6.Apply arrayOfVariantOfDouble409

Set move6 = product8.Move

Set move6 = move6.MovableObject

Dim arrayOfVariantOfDouble410(11)
arrayOfVariantOfDouble410(0) = 1.000000
arrayOfVariantOfDouble410(1) = 0.000000
arrayOfVariantOfDouble410(2) = 0.000000
arrayOfVariantOfDouble410(3) = 0.000000
arrayOfVariantOfDouble410(4) = 1.000000
arrayOfVariantOfDouble410(5) = 0.000000
arrayOfVariantOfDouble410(6) = 0.000000
arrayOfVariantOfDouble410(7) = 0.000000
arrayOfVariantOfDouble410(8) = 1.000000
arrayOfVariantOfDouble410(9) = 0.000000
arrayOfVariantOfDouble410(10) = 10.774126
arrayOfVariantOfDouble410(11) = 0.000000
move6.Apply arrayOfVariantOfDouble410

Set move6 = product8.Move

Set move6 = move6.MovableObject

Dim arrayOfVariantOfDouble411(11)
arrayOfVariantOfDouble411(0) = 1.000000
arrayOfVariantOfDouble411(1) = 0.000000
arrayOfVariantOfDouble411(2) = 0.000000
arrayOfVariantOfDouble411(3) = 0.000000
arrayOfVariantOfDouble411(4) = 1.000000
arrayOfVariantOfDouble411(5) = 0.000000
arrayOfVariantOfDouble411(6) = 0.000000
arrayOfVariantOfDouble411(7) = 0.000000
arrayOfVariantOfDouble411(8) = 1.000000
arrayOfVariantOfDouble411(9) = 0.000000
arrayOfVariantOfDouble411(10) = 9.925047
arrayOfVariantOfDouble411(11) = 0.000000
move6.Apply arrayOfVariantOfDouble411

Set move6 = product8.Move

Set move6 = move6.MovableObject

Dim arrayOfVariantOfDouble412(11)
arrayOfVariantOfDouble412(0) = 1.000000
arrayOfVariantOfDouble412(1) = 0.000000
arrayOfVariantOfDouble412(2) = 0.000000
arrayOfVariantOfDouble412(3) = 0.000000
arrayOfVariantOfDouble412(4) = 1.000000
arrayOfVariantOfDouble412(5) = 0.000000
arrayOfVariantOfDouble412(6) = 0.000000
arrayOfVariantOfDouble412(7) = 0.000000
arrayOfVariantOfDouble412(8) = 1.000000
arrayOfVariantOfDouble412(9) = 0.000000
arrayOfVariantOfDouble412(10) = 9.544479
arrayOfVariantOfDouble412(11) = 0.000000
move6.Apply arrayOfVariantOfDouble412

Set move6 = product8.Move

Set move6 = move6.MovableObject

Dim arrayOfVariantOfDouble413(11)
arrayOfVariantOfDouble413(0) = 1.000000
arrayOfVariantOfDouble413(1) = 0.000000
arrayOfVariantOfDouble413(2) = 0.000000
arrayOfVariantOfDouble413(3) = 0.000000
arrayOfVariantOfDouble413(4) = 1.000000
arrayOfVariantOfDouble413(5) = 0.000000
arrayOfVariantOfDouble413(6) = 0.000000
arrayOfVariantOfDouble413(7) = 0.000000
arrayOfVariantOfDouble413(8) = 1.000000
arrayOfVariantOfDouble413(9) = 0.000000
arrayOfVariantOfDouble413(10) = 8.695390
arrayOfVariantOfDouble413(11) = 0.000000
move6.Apply arrayOfVariantOfDouble413

Set move6 = product8.Move

Set move6 = move6.MovableObject

Dim arrayOfVariantOfDouble414(11)
arrayOfVariantOfDouble414(0) = 1.000000
arrayOfVariantOfDouble414(1) = 0.000000
arrayOfVariantOfDouble414(2) = 0.000000
arrayOfVariantOfDouble414(3) = 0.000000
arrayOfVariantOfDouble414(4) = 1.000000
arrayOfVariantOfDouble414(5) = 0.000000
arrayOfVariantOfDouble414(6) = 0.000000
arrayOfVariantOfDouble414(7) = 0.000000
arrayOfVariantOfDouble414(8) = 1.000000
arrayOfVariantOfDouble414(9) = 0.000000
arrayOfVariantOfDouble414(10) = 6.236149
arrayOfVariantOfDouble414(11) = 0.000000
move6.Apply arrayOfVariantOfDouble414

Set move6 = product8.Move

Set move6 = move6.MovableObject

Dim arrayOfVariantOfDouble415(11)
arrayOfVariantOfDouble415(0) = 1.000000
arrayOfVariantOfDouble415(1) = 0.000000
arrayOfVariantOfDouble415(2) = 0.000000
arrayOfVariantOfDouble415(3) = 0.000000
arrayOfVariantOfDouble415(4) = 1.000000
arrayOfVariantOfDouble415(5) = 0.000000
arrayOfVariantOfDouble415(6) = 0.000000
arrayOfVariantOfDouble415(7) = 0.000000
arrayOfVariantOfDouble415(8) = 1.000000
arrayOfVariantOfDouble415(9) = 0.000000
arrayOfVariantOfDouble415(10) = 5.387030
arrayOfVariantOfDouble415(11) = 0.000000
move6.Apply arrayOfVariantOfDouble415

Set move6 = product8.Move

Set move6 = move6.MovableObject

Dim arrayOfVariantOfDouble416(11)
arrayOfVariantOfDouble416(0) = 1.000000
arrayOfVariantOfDouble416(1) = 0.000000
arrayOfVariantOfDouble416(2) = 0.000000
arrayOfVariantOfDouble416(3) = 0.000000
arrayOfVariantOfDouble416(4) = 1.000000
arrayOfVariantOfDouble416(5) = 0.000000
arrayOfVariantOfDouble416(6) = 0.000000
arrayOfVariantOfDouble416(7) = 0.000000
arrayOfVariantOfDouble416(8) = 1.000000
arrayOfVariantOfDouble416(9) = 0.000000
arrayOfVariantOfDouble416(10) = 4.157413
arrayOfVariantOfDouble416(11) = 0.000000
move6.Apply arrayOfVariantOfDouble416

Set move6 = product8.Move

Set move6 = move6.MovableObject

Dim arrayOfVariantOfDouble417(11)
arrayOfVariantOfDouble417(0) = 1.000000
arrayOfVariantOfDouble417(1) = 0.000000
arrayOfVariantOfDouble417(2) = 0.000000
arrayOfVariantOfDouble417(3) = 0.000000
arrayOfVariantOfDouble417(4) = 1.000000
arrayOfVariantOfDouble417(5) = 0.000000
arrayOfVariantOfDouble417(6) = 0.000000
arrayOfVariantOfDouble417(7) = 0.000000
arrayOfVariantOfDouble417(8) = 1.000000
arrayOfVariantOfDouble417(9) = 0.000000
arrayOfVariantOfDouble417(10) = 1.229645
arrayOfVariantOfDouble417(11) = 0.000000
move6.Apply arrayOfVariantOfDouble417

Set move6 = product8.Move

Set move6 = move6.MovableObject

Dim arrayOfVariantOfDouble418(11)
arrayOfVariantOfDouble418(0) = 1.000000
arrayOfVariantOfDouble418(1) = 0.000000
arrayOfVariantOfDouble418(2) = 0.000000
arrayOfVariantOfDouble418(3) = 0.000000
arrayOfVariantOfDouble418(4) = 1.000000
arrayOfVariantOfDouble418(5) = 0.000000
arrayOfVariantOfDouble418(6) = 0.000000
arrayOfVariantOfDouble418(7) = 0.000000
arrayOfVariantOfDouble418(8) = 1.000000
arrayOfVariantOfDouble418(9) = 0.000000
arrayOfVariantOfDouble418(10) = 2.927779
arrayOfVariantOfDouble418(11) = 0.000000
move6.Apply arrayOfVariantOfDouble418

Set move6 = product8.Move

Set move6 = move6.MovableObject

Dim arrayOfVariantOfDouble419(11)
arrayOfVariantOfDouble419(0) = 1.000000
arrayOfVariantOfDouble419(1) = 0.000000
arrayOfVariantOfDouble419(2) = 0.000000
arrayOfVariantOfDouble419(3) = 0.000000
arrayOfVariantOfDouble419(4) = 1.000000
arrayOfVariantOfDouble419(5) = 0.000000
arrayOfVariantOfDouble419(6) = 0.000000
arrayOfVariantOfDouble419(7) = 0.000000
arrayOfVariantOfDouble419(8) = 1.000000
arrayOfVariantOfDouble419(9) = 0.000000
arrayOfVariantOfDouble419(10) = 2.459289
arrayOfVariantOfDouble419(11) = 0.000000
move6.Apply arrayOfVariantOfDouble419

Set move6 = product8.Move

Set move6 = move6.MovableObject

Dim arrayOfVariantOfDouble420(11)
arrayOfVariantOfDouble420(0) = 1.000000
arrayOfVariantOfDouble420(1) = 0.000000
arrayOfVariantOfDouble420(2) = 0.000000
arrayOfVariantOfDouble420(3) = 0.000000
arrayOfVariantOfDouble420(4) = 1.000000
arrayOfVariantOfDouble420(5) = 0.000000
arrayOfVariantOfDouble420(6) = 0.000000
arrayOfVariantOfDouble420(7) = 0.000000
arrayOfVariantOfDouble420(8) = 1.000000
arrayOfVariantOfDouble420(9) = 0.000000
arrayOfVariantOfDouble420(10) = 3.308365
arrayOfVariantOfDouble420(11) = 0.000000
move6.Apply arrayOfVariantOfDouble420

Set move6 = product8.Move

Set move6 = move6.MovableObject

Dim arrayOfVariantOfDouble421(11)
arrayOfVariantOfDouble421(0) = 1.000000
arrayOfVariantOfDouble421(1) = 0.000000
arrayOfVariantOfDouble421(2) = 0.000000
arrayOfVariantOfDouble421(3) = 0.000000
arrayOfVariantOfDouble421(4) = 1.000000
arrayOfVariantOfDouble421(5) = 0.000000
arrayOfVariantOfDouble421(6) = 0.000000
arrayOfVariantOfDouble421(7) = 0.000000
arrayOfVariantOfDouble421(8) = 1.000000
arrayOfVariantOfDouble421(9) = 0.000000
arrayOfVariantOfDouble421(10) = 3.308341
arrayOfVariantOfDouble421(11) = 0.000000
move6.Apply arrayOfVariantOfDouble421

Set move6 = product8.Move

Set move6 = move6.MovableObject

Dim arrayOfVariantOfDouble422(11)
arrayOfVariantOfDouble422(0) = 1.000000
arrayOfVariantOfDouble422(1) = 0.000000
arrayOfVariantOfDouble422(2) = 0.000000
arrayOfVariantOfDouble422(3) = 0.000000
arrayOfVariantOfDouble422(4) = 1.000000
arrayOfVariantOfDouble422(5) = 0.000000
arrayOfVariantOfDouble422(6) = 0.000000
arrayOfVariantOfDouble422(7) = 0.000000
arrayOfVariantOfDouble422(8) = 1.000000
arrayOfVariantOfDouble422(9) = 0.000000
arrayOfVariantOfDouble422(10) = 6.616701
arrayOfVariantOfDouble422(11) = 0.000000
move6.Apply arrayOfVariantOfDouble422

Set move6 = product8.Move

Set move6 = move6.MovableObject

Dim arrayOfVariantOfDouble423(11)
arrayOfVariantOfDouble423(0) = 1.000000
arrayOfVariantOfDouble423(1) = 0.000000
arrayOfVariantOfDouble423(2) = 0.000000
arrayOfVariantOfDouble423(3) = 0.000000
arrayOfVariantOfDouble423(4) = 1.000000
arrayOfVariantOfDouble423(5) = 0.000000
arrayOfVariantOfDouble423(6) = 0.000000
arrayOfVariantOfDouble423(7) = 0.000000
arrayOfVariantOfDouble423(8) = 1.000000
arrayOfVariantOfDouble423(9) = 0.000000
arrayOfVariantOfDouble423(10) = 5.767624
arrayOfVariantOfDouble423(11) = 0.000000
move6.Apply arrayOfVariantOfDouble423

Set move6 = product8.Move

Set move6 = move6.MovableObject

Dim arrayOfVariantOfDouble424(11)
arrayOfVariantOfDouble424(0) = 1.000000
arrayOfVariantOfDouble424(1) = 0.000000
arrayOfVariantOfDouble424(2) = 0.000000
arrayOfVariantOfDouble424(3) = 0.000000
arrayOfVariantOfDouble424(4) = 1.000000
arrayOfVariantOfDouble424(5) = 0.000000
arrayOfVariantOfDouble424(6) = 0.000000
arrayOfVariantOfDouble424(7) = 0.000000
arrayOfVariantOfDouble424(8) = 1.000000
arrayOfVariantOfDouble424(9) = 0.000000
arrayOfVariantOfDouble424(10) = 4.537982
arrayOfVariantOfDouble424(11) = 0.000000
move6.Apply arrayOfVariantOfDouble424

Set move6 = product8.Move

Set move6 = move6.MovableObject

Dim arrayOfVariantOfDouble425(11)
arrayOfVariantOfDouble425(0) = 1.000000
arrayOfVariantOfDouble425(1) = 0.000000
arrayOfVariantOfDouble425(2) = 0.000000
arrayOfVariantOfDouble425(3) = 0.000000
arrayOfVariantOfDouble425(4) = 1.000000
arrayOfVariantOfDouble425(5) = 0.000000
arrayOfVariantOfDouble425(6) = 0.000000
arrayOfVariantOfDouble425(7) = 0.000000
arrayOfVariantOfDouble425(8) = 1.000000
arrayOfVariantOfDouble425(9) = 0.000000
arrayOfVariantOfDouble425(10) = 10.305652
arrayOfVariantOfDouble425(11) = 0.000000
move6.Apply arrayOfVariantOfDouble425

Set move6 = product8.Move

Set move6 = move6.MovableObject

Dim arrayOfVariantOfDouble426(11)
arrayOfVariantOfDouble426(0) = 1.000000
arrayOfVariantOfDouble426(1) = 0.000000
arrayOfVariantOfDouble426(2) = 0.000000
arrayOfVariantOfDouble426(3) = 0.000000
arrayOfVariantOfDouble426(4) = 1.000000
arrayOfVariantOfDouble426(5) = 0.000000
arrayOfVariantOfDouble426(6) = 0.000000
arrayOfVariantOfDouble426(7) = 0.000000
arrayOfVariantOfDouble426(8) = 1.000000
arrayOfVariantOfDouble426(9) = 0.000000
arrayOfVariantOfDouble426(10) = 8.226882
arrayOfVariantOfDouble426(11) = 0.000000
move6.Apply arrayOfVariantOfDouble426

Set move6 = product8.Move

Set move6 = move6.MovableObject

Dim arrayOfVariantOfDouble427(11)
arrayOfVariantOfDouble427(0) = 1.000000
arrayOfVariantOfDouble427(1) = 0.000000
arrayOfVariantOfDouble427(2) = 0.000000
arrayOfVariantOfDouble427(3) = 0.000000
arrayOfVariantOfDouble427(4) = 1.000000
arrayOfVariantOfDouble427(5) = 0.000000
arrayOfVariantOfDouble427(6) = 0.000000
arrayOfVariantOfDouble427(7) = 0.000000
arrayOfVariantOfDouble427(8) = 1.000000
arrayOfVariantOfDouble427(9) = 0.000000
arrayOfVariantOfDouble427(10) = 10.305639
arrayOfVariantOfDouble427(11) = 0.000000
move6.Apply arrayOfVariantOfDouble427

Set move6 = product8.Move

Set move6 = move6.MovableObject

Dim arrayOfVariantOfDouble428(11)
arrayOfVariantOfDouble428(0) = 1.000000
arrayOfVariantOfDouble428(1) = 0.000000
arrayOfVariantOfDouble428(2) = 0.000000
arrayOfVariantOfDouble428(3) = 0.000000
arrayOfVariantOfDouble428(4) = 1.000000
arrayOfVariantOfDouble428(5) = 0.000000
arrayOfVariantOfDouble428(6) = 0.000000
arrayOfVariantOfDouble428(7) = 0.000000
arrayOfVariantOfDouble428(8) = 1.000000
arrayOfVariantOfDouble428(9) = 0.000000
arrayOfVariantOfDouble428(10) = 14.463030
arrayOfVariantOfDouble428(11) = 0.000000
move6.Apply arrayOfVariantOfDouble428

Set move6 = product8.Move

Set move6 = move6.MovableObject

Dim arrayOfVariantOfDouble429(11)
arrayOfVariantOfDouble429(0) = 1.000000
arrayOfVariantOfDouble429(1) = 0.000000
arrayOfVariantOfDouble429(2) = 0.000000
arrayOfVariantOfDouble429(3) = 0.000000
arrayOfVariantOfDouble429(4) = 1.000000
arrayOfVariantOfDouble429(5) = 0.000000
arrayOfVariantOfDouble429(6) = 0.000000
arrayOfVariantOfDouble429(7) = 0.000000
arrayOfVariantOfDouble429(8) = 1.000000
arrayOfVariantOfDouble429(9) = 0.000000
arrayOfVariantOfDouble429(10) = 14.843626
arrayOfVariantOfDouble429(11) = 0.000000
move6.Apply arrayOfVariantOfDouble429

Set move6 = product8.Move

Set move6 = move6.MovableObject

Dim arrayOfVariantOfDouble430(11)
arrayOfVariantOfDouble430(0) = 1.000000
arrayOfVariantOfDouble430(1) = 0.000000
arrayOfVariantOfDouble430(2) = 0.000000
arrayOfVariantOfDouble430(3) = 0.000000
arrayOfVariantOfDouble430(4) = 1.000000
arrayOfVariantOfDouble430(5) = 0.000000
arrayOfVariantOfDouble430(6) = 0.000000
arrayOfVariantOfDouble430(7) = 0.000000
arrayOfVariantOfDouble430(8) = 1.000000
arrayOfVariantOfDouble430(9) = 0.000000
arrayOfVariantOfDouble430(10) = 10.305597
arrayOfVariantOfDouble430(11) = 0.000000
move6.Apply arrayOfVariantOfDouble430

Set move6 = product8.Move

Set move6 = move6.MovableObject

Dim arrayOfVariantOfDouble431(11)
arrayOfVariantOfDouble431(0) = 1.000000
arrayOfVariantOfDouble431(1) = 0.000000
arrayOfVariantOfDouble431(2) = 0.000000
arrayOfVariantOfDouble431(3) = 0.000000
arrayOfVariantOfDouble431(4) = 1.000000
arrayOfVariantOfDouble431(5) = 0.000000
arrayOfVariantOfDouble431(6) = 0.000000
arrayOfVariantOfDouble431(7) = 0.000000
arrayOfVariantOfDouble431(8) = 1.000000
arrayOfVariantOfDouble431(9) = 0.000000
arrayOfVariantOfDouble431(10) = 7.846362
arrayOfVariantOfDouble431(11) = 0.000000
move6.Apply arrayOfVariantOfDouble431

Set move6 = product8.Move

Set move6 = move6.MovableObject

Dim arrayOfVariantOfDouble432(11)
arrayOfVariantOfDouble432(0) = 1.000000
arrayOfVariantOfDouble432(1) = 0.000000
arrayOfVariantOfDouble432(2) = 0.000000
arrayOfVariantOfDouble432(3) = 0.000000
arrayOfVariantOfDouble432(4) = 1.000000
arrayOfVariantOfDouble432(5) = 0.000000
arrayOfVariantOfDouble432(6) = 0.000000
arrayOfVariantOfDouble432(7) = 0.000000
arrayOfVariantOfDouble432(8) = 1.000000
arrayOfVariantOfDouble432(9) = 0.000000
arrayOfVariantOfDouble432(10) = 8.226916
arrayOfVariantOfDouble432(11) = 0.000000
move6.Apply arrayOfVariantOfDouble432

Set move6 = product8.Move

Set move6 = move6.MovableObject

Dim arrayOfVariantOfDouble433(11)
arrayOfVariantOfDouble433(0) = 1.000000
arrayOfVariantOfDouble433(1) = 0.000000
arrayOfVariantOfDouble433(2) = 0.000000
arrayOfVariantOfDouble433(3) = 0.000000
arrayOfVariantOfDouble433(4) = 1.000000
arrayOfVariantOfDouble433(5) = 0.000000
arrayOfVariantOfDouble433(6) = 0.000000
arrayOfVariantOfDouble433(7) = 0.000000
arrayOfVariantOfDouble433(8) = 1.000000
arrayOfVariantOfDouble433(9) = 0.000000
arrayOfVariantOfDouble433(10) = 5.767622
arrayOfVariantOfDouble433(11) = 0.000000
move6.Apply arrayOfVariantOfDouble433

Set move6 = product8.Move

Set move6 = move6.MovableObject

Dim arrayOfVariantOfDouble434(11)
arrayOfVariantOfDouble434(0) = 1.000000
arrayOfVariantOfDouble434(1) = 0.000000
arrayOfVariantOfDouble434(2) = 0.000000
arrayOfVariantOfDouble434(3) = 0.000000
arrayOfVariantOfDouble434(4) = 1.000000
arrayOfVariantOfDouble434(5) = 0.000000
arrayOfVariantOfDouble434(6) = 0.000000
arrayOfVariantOfDouble434(7) = 0.000000
arrayOfVariantOfDouble434(8) = 1.000000
arrayOfVariantOfDouble434(9) = 0.000000
arrayOfVariantOfDouble434(10) = 5.767621
arrayOfVariantOfDouble434(11) = 0.000000
move6.Apply arrayOfVariantOfDouble434

Set move6 = product8.Move

Set move6 = move6.MovableObject

Dim arrayOfVariantOfDouble435(11)
arrayOfVariantOfDouble435(0) = 1.000000
arrayOfVariantOfDouble435(1) = 0.000000
arrayOfVariantOfDouble435(2) = 0.000000
arrayOfVariantOfDouble435(3) = 0.000000
arrayOfVariantOfDouble435(4) = 1.000000
arrayOfVariantOfDouble435(5) = 0.000000
arrayOfVariantOfDouble435(6) = 0.000000
arrayOfVariantOfDouble435(7) = 0.000000
arrayOfVariantOfDouble435(8) = 1.000000
arrayOfVariantOfDouble435(9) = 0.000000
arrayOfVariantOfDouble435(10) = 5.767673
arrayOfVariantOfDouble435(11) = 0.000000
move6.Apply arrayOfVariantOfDouble435

Set move6 = product8.Move

Set move6 = move6.MovableObject

Dim arrayOfVariantOfDouble436(11)
arrayOfVariantOfDouble436(0) = 1.000000
arrayOfVariantOfDouble436(1) = 0.000000
arrayOfVariantOfDouble436(2) = 0.000000
arrayOfVariantOfDouble436(3) = 0.000000
arrayOfVariantOfDouble436(4) = 1.000000
arrayOfVariantOfDouble436(5) = 0.000000
arrayOfVariantOfDouble436(6) = 0.000000
arrayOfVariantOfDouble436(7) = 0.000000
arrayOfVariantOfDouble436(8) = 1.000000
arrayOfVariantOfDouble436(9) = 0.000000
arrayOfVariantOfDouble436(10) = 5.387029
arrayOfVariantOfDouble436(11) = 0.000000
move6.Apply arrayOfVariantOfDouble436

Set move6 = product8.Move

Set move6 = move6.MovableObject

Dim arrayOfVariantOfDouble437(11)
arrayOfVariantOfDouble437(0) = 1.000000
arrayOfVariantOfDouble437(1) = 0.000000
arrayOfVariantOfDouble437(2) = 0.000000
arrayOfVariantOfDouble437(3) = 0.000000
arrayOfVariantOfDouble437(4) = 1.000000
arrayOfVariantOfDouble437(5) = 0.000000
arrayOfVariantOfDouble437(6) = 0.000000
arrayOfVariantOfDouble437(7) = 0.000000
arrayOfVariantOfDouble437(8) = 1.000000
arrayOfVariantOfDouble437(9) = 0.000000
arrayOfVariantOfDouble437(10) = 2.459283
arrayOfVariantOfDouble437(11) = 0.000000
move6.Apply arrayOfVariantOfDouble437

Set move6 = product8.Move

Set move6 = move6.MovableObject

Dim arrayOfVariantOfDouble438(11)
arrayOfVariantOfDouble438(0) = 1.000000
arrayOfVariantOfDouble438(1) = 0.000000
arrayOfVariantOfDouble438(2) = 0.000000
arrayOfVariantOfDouble438(3) = 0.000000
arrayOfVariantOfDouble438(4) = 1.000000
arrayOfVariantOfDouble438(5) = 0.000000
arrayOfVariantOfDouble438(6) = 0.000000
arrayOfVariantOfDouble438(7) = 0.000000
arrayOfVariantOfDouble438(8) = 1.000000
arrayOfVariantOfDouble438(9) = 0.000000
arrayOfVariantOfDouble438(10) = 1.229656
arrayOfVariantOfDouble438(11) = 0.000000
move6.Apply arrayOfVariantOfDouble438

Set constraints1 = product1.Connections("CATIAConstraints")

Set reference6 = product1.CreateReferenceFromName("A2/DM.1/!Axis:(Selection_RSur:(Face:(Brp:(Pocket.2;0:(Brp:(Sketch.3;8)));None:();Cf11:());Pocket.2_ResultOUT;Z0;G4162))")

Dim reference52 As Reference
Set reference52 = product1.CreateReferenceFromName("A2/Bolt.6/!Axis:(Selection_RSur:(Face:(Brp:(Shaft.1;0:(Brp:(Sketch.1;10)));None:();Cf11:());Pad.1_ResultOUT;Z0;G4162))")

Dim constraint35 As Constraint
Set constraint35 = constraints1.AddBiEltCst(catCstTypeOn, reference6, reference52)

Set constraints1 = product1.Connections("CATIAConstraints")

Set reference45 = product1.CreateReferenceFromName("A2/DM.1/!Selection_RSur:(Face:(Brp:(Pad.1;0:(Brp:(Sketch.1;8)));None:();Cf11:());Pocket.2_ResultOUT;Z0;G4162)")

Dim reference53 As Reference
Set reference53 = product1.CreateReferenceFromName("A2/Bolt.6/!Selection_RSur:(Face:(Brp:(Shaft.1;0:(Brp:(Sketch.1;8)));None:();Cf11:());Pad.1_ResultOUT;Z0;G4162)")

Dim constraint36 As Constraint
Set constraint36 = constraints1.AddBiEltCst(catCstTypeSurfContact, reference45, reference53)

product1.Update 

Set constraints1 = product1.Connections("CATIAConstraints")

Dim reference54 As Reference
Set reference54 = product1.CreateReferenceFromName("A2/Bolt.6/!Selection_REdge:(Edge:(Face:(Brp:(Pad.1;0:(Brp:(Sketch.2;10)));None:();Cf11:());Face:(Brp:(Pad.1;2);None:();Cf11:());None:(Limits1:();Limits2:());Cf11:());Pad.1_ResultOUT;Z0;G4162)")

Set reference48 = product1.CreateReferenceFromName("A2/Plate.1/!Selection_REdge:(Edge:(Face:(Brp:(Pad.1;1);None:();Cf11:());Face:(Brp:(Pad.1;0:(Brp:(Sketch.1;6)));None:();Cf11:());None:(Limits1:();Limits2:());Cf11:());Pad.1_ResultOUT;Z0;G4162)")

Dim constraint37 As Constraint
Set constraint37 = constraints1.AddBiEltCst(catCstTypeAngle, reference54, reference48)

Dim angle8 As Dimension
Set angle8 = constraint37.Dimension

angle8.Value = 0.000000

product1.Update 



End Sub
