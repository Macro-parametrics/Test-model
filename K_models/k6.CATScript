Language = "VBSCRIPT"
Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements 

Dim shapeFactory1 As Factory
Set shapeFactory1 = part1.ShapeFactory

Dim reference1 As AnyObject
Set reference1 = originElements1.PlaneXY


Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(-62.500000, -62.500000)

point2D1.ReportName = 3

Dim point2D2 As Point2D
Set point2D2 = factory2D1.CreatePoint(62.500000, -62.500000)

point2D2.ReportName = 4

Dim line2D3 As Line2D
Set line2D3 = factory2D1.CreateLine(-62.500000, -62.500000, 62.500000, -62.500000)

line2D3.ReportName = 5

line2D3.StartPoint = point2D1

line2D3.EndPoint = point2D2

Dim point2D3 As Point2D
Set point2D3 = factory2D1.CreatePoint(62.500000, -62.500000)

point2D3.ReportName = 6

Dim point2D4 As Point2D
Set point2D4 = factory2D1.CreatePoint(62.500000, 62.500000)

point2D4.ReportName = 7

Dim line2D4 As Line2D
Set line2D4 = factory2D1.CreateLine(62.500000, -62.500000, 62.500000, 62.500000)

line2D4.ReportName = 8

line2D4.StartPoint = point2D3

line2D4.EndPoint = point2D4

Dim point2D5 As Point2D
Set point2D5 = factory2D1.CreatePoint(62.500000, 62.500000)

point2D5.ReportName = 9

Dim point2D6 As Point2D
Set point2D6 = factory2D1.CreatePoint(-62.500000, 62.500000)

point2D6.ReportName = 10

Dim line2D5 As Line2D
Set line2D5 = factory2D1.CreateLine(62.500000, 62.500000, -62.500000, 62.500000)

line2D5.ReportName = 11

line2D5.StartPoint = point2D5

line2D5.EndPoint = point2D6

Dim point2D7 As Point2D
Set point2D7 = factory2D1.CreatePoint(-62.500000, 62.500000)

point2D7.ReportName = 12

Dim point2D8 As Point2D
Set point2D8 = factory2D1.CreatePoint(-62.500000, -62.500000)

point2D8.ReportName = 13

Dim line2D6 As Line2D
Set line2D6 = factory2D1.CreateLine(-62.500000, 62.500000, -62.500000, -62.500000)

line2D6.ReportName = 14

line2D6.StartPoint = point2D7

line2D6.EndPoint = point2D8

sketch1.CloseEdition 

part1.InWorkObject = body1

part1.Update

Dim pad1 As Pad
Set pad1 = shapeFactory1.AddNewPad(sketch1, 0.0)

Dim limit1 As Limit
Set limit1 = pad1.FirstLimit

limit1.LimitMode = catOffsetLimit

Dim length1 As Length
Set length1 = limit1.Dimension

length1.Value = 42.180000

Dim limit2 As Limit
Set limit2 = pad1.SecondLimit

limit2.LimitMode = catOffsetLimit

pad1.DirectionOrientation = catRegularOrientation

part1.Update

Dim reference2 As Reference
Set reference2 = part1.CreateReferenceFromName("Selection_RSur:(Face:(Brp:(Pad.1;2);None:();Cf11:());Pad.1_ResultOUT;Z0;G3563)")

Dim sketch2 As Sketch
Set sketch2 = sketches1.Add(reference2)

Dim arrayOfVariantOfDouble2(8)
arrayOfVariantOfDouble2(0) = 0.000000
arrayOfVariantOfDouble2(1) = 0.000000
arrayOfVariantOfDouble2(2) = 42.180000
arrayOfVariantOfDouble2(3) = 1.000000
arrayOfVariantOfDouble2(4) = 0.000000
arrayOfVariantOfDouble2(5) = 0.000000
arrayOfVariantOfDouble2(6) = 0.000000
arrayOfVariantOfDouble2(7) = 1.000000
arrayOfVariantOfDouble2(8) = 0.000000
sketch2.SetAbsoluteAxisData arrayOfVariantOfDouble2

Dim factory2D2 As Factory2D
Set factory2D2 = sketch2.OpenEdition()

Dim geometricElements2 As GeometricElements
Set geometricElements2 = sketch2.GeometricElements

Dim axis2D2 As GeometricElement
Set axis2D2 = geometricElements2.Item("AbsoluteAxis")

Dim line2D7 As CATBaseDispatch
Set line2D7 = axis2D2.GetItem("HDirection")

line2D7.ReportName = 1

Dim line2D8 As CATBaseDispatch
Set line2D8 = axis2D2.GetItem("VDirection")

line2D8.ReportName = 2

Dim point2D9 As Point2D
Set point2D9 = factory2D2.CreatePoint(0.000000, 0.000000)

point2D9.ReportName = 3

Dim circle2D1 As Circle2D
Set circle2D1 = factory2D2.CreateClosedCircle(0.000000, 0.000000, 40.500000)

circle2D1.ReportName = 4

sketch2.CloseEdition 

part1.InWorkObject = body1

part1.Update

Dim pad2 As Pad
Set pad2 = shapeFactory1.AddNewPad(sketch2, 0.0)

Dim limit3 As Limit
Set limit3 = pad2.FirstLimit

limit3.LimitMode = catOffsetLimit

Dim length2 As Length
Set length2 = limit3.Dimension

length2.Value = 190.640000

Dim limit4 As Limit
Set limit4 = pad2.SecondLimit

limit4.LimitMode = catOffsetLimit

pad2.DirectionOrientation = catRegularOrientation

part1.Update

Dim reference3 As Reference
Set reference3 = part1.CreateReferenceFromName("Selection_RSur:(Face:(Brp:(Pad.2;2);None:();Cf11:());Pad.2_ResultOUT;Z0;G3563)")

Dim sketch3 As Sketch
Set sketch3 = sketches1.Add(reference3)

Dim arrayOfVariantOfDouble3(8)
arrayOfVariantOfDouble3(0) = 0.000000
arrayOfVariantOfDouble3(1) = 0.000000
arrayOfVariantOfDouble3(2) = 232.820000
arrayOfVariantOfDouble3(3) = 1.000000
arrayOfVariantOfDouble3(4) = 0.000000
arrayOfVariantOfDouble3(5) = 0.000000
arrayOfVariantOfDouble3(6) = 0.000000
arrayOfVariantOfDouble3(7) = 1.000000
arrayOfVariantOfDouble3(8) = 0.000000
sketch3.SetAbsoluteAxisData arrayOfVariantOfDouble3

Dim factory2D3 As Factory2D
Set factory2D3 = sketch3.OpenEdition()

Dim geometricElements3 As GeometricElements
Set geometricElements3 = sketch3.GeometricElements

Dim axis2D3 As GeometricElement
Set axis2D3 = geometricElements3.Item("AbsoluteAxis")

Dim line2D9 As CATBaseDispatch
Set line2D9 = axis2D3.GetItem("HDirection")

line2D9.ReportName = 1

Dim line2D10 As CATBaseDispatch
Set line2D10 = axis2D3.GetItem("VDirection")

line2D10.ReportName = 2

Dim point2D10 As Point2D
Set point2D10 = factory2D3.CreatePoint(-62.500000, -62.500000)

point2D10.ReportName = 3

Dim point2D11 As Point2D
Set point2D11 = factory2D3.CreatePoint(62.500000, -62.500000)

point2D11.ReportName = 4

Dim line2D11 As Line2D
Set line2D11 = factory2D3.CreateLine(-62.500000, -62.500000, 62.500000, -62.500000)

line2D11.ReportName = 5

line2D11.StartPoint = point2D10

line2D11.EndPoint = point2D11

Dim point2D12 As Point2D
Set point2D12 = factory2D3.CreatePoint(62.500000, -62.500000)

point2D12.ReportName = 6

Dim point2D13 As Point2D
Set point2D13 = factory2D3.CreatePoint(62.500000, 62.500000)

point2D13.ReportName = 7

Dim line2D12 As Line2D
Set line2D12 = factory2D3.CreateLine(62.500000, -62.500000, 62.500000, 62.500000)

line2D12.ReportName = 8

line2D12.StartPoint = point2D12

line2D12.EndPoint = point2D13

Dim point2D14 As Point2D
Set point2D14 = factory2D3.CreatePoint(62.500000, 62.500000)

point2D14.ReportName = 9

Dim point2D15 As Point2D
Set point2D15 = factory2D3.CreatePoint(-62.500000, 62.500000)

point2D15.ReportName = 10

Dim line2D13 As Line2D
Set line2D13 = factory2D3.CreateLine(62.500000, 62.500000, -62.500000, 62.500000)

line2D13.ReportName = 11

line2D13.StartPoint = point2D14

line2D13.EndPoint = point2D15

Dim point2D16 As Point2D
Set point2D16 = factory2D3.CreatePoint(-62.500000, 62.500000)

point2D16.ReportName = 12

Dim point2D17 As Point2D
Set point2D17 = factory2D3.CreatePoint(-62.500000, -62.500000)

point2D17.ReportName = 13

Dim line2D14 As Line2D
Set line2D14 = factory2D3.CreateLine(-62.500000, 62.500000, -62.500000, -62.500000)

line2D14.ReportName = 14

line2D14.StartPoint = point2D16

line2D14.EndPoint = point2D17

sketch3.CloseEdition 

part1.InWorkObject = body1

part1.Update

Dim pad3 As Pad
Set pad3 = shapeFactory1.AddNewPad(sketch3, 0.0)

Dim limit5 As Limit
Set limit5 = pad3.FirstLimit

limit5.LimitMode = catOffsetLimit

Dim length3 As Length
Set length3 = limit5.Dimension

length3.Value = 42.180000

Dim limit6 As Limit
Set limit6 = pad3.SecondLimit

limit6.LimitMode = catOffsetLimit

pad3.DirectionOrientation = catRegularOrientation

part1.Update

Dim reference4 As Reference
Set reference4 = part1.CreateReferenceFromName("Selection_RSur:(Face:(Brp:(Pad.1;2);None:();Cf11:());Pad.1_ResultOUT;Z0;G3563)")

Dim sketch4 As Sketch
Set sketch4 = sketches1.Add(reference4)

Dim arrayOfVariantOfDouble4(8)
arrayOfVariantOfDouble4(0) = 0.000000
arrayOfVariantOfDouble4(1) = 0.000000
arrayOfVariantOfDouble4(2) = 42.180000
arrayOfVariantOfDouble4(3) = 1.000000
arrayOfVariantOfDouble4(4) = 0.000000
arrayOfVariantOfDouble4(5) = 0.000000
arrayOfVariantOfDouble4(6) = 0.000000
arrayOfVariantOfDouble4(7) = 1.000000
arrayOfVariantOfDouble4(8) = 0.000000
sketch4.SetAbsoluteAxisData arrayOfVariantOfDouble4

Dim factory2D4 As Factory2D
Set factory2D4 = sketch4.OpenEdition()

Dim geometricElements4 As GeometricElements
Set geometricElements4 = sketch4.GeometricElements

Dim axis2D4 As GeometricElement
Set axis2D4 = geometricElements4.Item("AbsoluteAxis")

Dim line2D15 As CATBaseDispatch
Set line2D15 = axis2D4.GetItem("HDirection")

line2D15.ReportName = 1

Dim line2D16 As CATBaseDispatch
Set line2D16 = axis2D4.GetItem("VDirection")

line2D16.ReportName = 2

Dim point2D18 As Point2D
Set point2D18 = factory2D4.CreatePoint(48.250000, 12.050000)

point2D18.ReportName = 3

Dim circle2D2 As Circle2D
Set circle2D2 = factory2D4.CreateClosedCircle(48.250000, 12.050000, 5.175000)

circle2D2.ReportName = 4

sketch4.CloseEdition 

part1.InWorkObject = body1

part1.Update

Dim pad4 As Pad
Set pad4 = shapeFactory1.AddNewPad(sketch4, 0.0)

Dim limit7 As Limit
Set limit7 = pad4.FirstLimit

limit7.LimitMode = catOffsetLimit

Dim length4 As Length
Set length4 = limit7.Dimension

length4.Value = 190.640000

Dim limit8 As Limit
Set limit8 = pad4.SecondLimit

limit8.LimitMode = catOffsetLimit

pad4.DirectionOrientation = catRegularOrientation

part1.Update

Dim reference5 As Reference
Set reference5 = part1.CreateReferenceFromName("")

Dim reference6 As Reference
Set reference6 = part1.CreateReferenceFromName("")

Dim circPattern1 As CircPattern
Set circPattern1 = shapeFactory1.AddNewCircPattern(pad4, 1, 4.0, 20, 90.0, 1, 1, reference5, reference6, True, 0, True)

circPattern1.CircularPatternParameters = catInstancesandAngularSpacing

Dim reference7 As Reference
Set reference7 = originElements1.PlaneXY

circPattern1.SetRotationAxis reference7

part1.Update

Dim reference8 As Reference
Set reference8 = part1.CreateReferenceFromName("Selection_RSur:(Face:(Brp:(Pad.3;2);None:();Cf11:());Pad.3_ResultOUT;Z0;G3563)")

Dim sketch5 As Sketch
Set sketch5 = sketches1.Add(reference8)

Dim arrayOfVariantOfDouble5(8)
arrayOfVariantOfDouble5(0) = 0.000000
arrayOfVariantOfDouble5(1) = 0.000000
arrayOfVariantOfDouble5(2) = 275.000000
arrayOfVariantOfDouble5(3) = 1.000000
arrayOfVariantOfDouble5(4) = 0.000000
arrayOfVariantOfDouble5(5) = 0.000000
arrayOfVariantOfDouble5(6) = 0.000000
arrayOfVariantOfDouble5(7) = 1.000000
arrayOfVariantOfDouble5(8) = 0.000000
sketch5.SetAbsoluteAxisData arrayOfVariantOfDouble5

Dim factory2D5 As Factory2D
Set factory2D5 = sketch5.OpenEdition()

Dim geometricElements5 As GeometricElements
Set geometricElements5 = sketch5.GeometricElements

Dim axis2D5 As GeometricElement
Set axis2D5 = geometricElements5.Item("AbsoluteAxis")

Dim line2D17 As CATBaseDispatch
Set line2D17 = axis2D5.GetItem("HDirection")

line2D17.ReportName = 1

Dim line2D18 As CATBaseDispatch
Set line2D18 = axis2D5.GetItem("VDirection")

line2D18.ReportName = 2

Dim point2D19 As Point2D
Set point2D19 = factory2D5.CreatePoint(0.000000, 0.000000)

point2D19.ReportName = 3

Dim circle2D3 As Circle2D
Set circle2D3 = factory2D5.CreateClosedCircle(0.000000, 0.000000, 15.625000)

circle2D3.ReportName = 4

sketch5.CloseEdition 

part1.InWorkObject = body1

part1.Update

Dim pad5 As Pad
Set pad5 = shapeFactory1.AddNewPad(sketch5, 0.0)

Dim limit9 As Limit
Set limit9 = pad5.FirstLimit

limit9.LimitMode = catOffsetLimit

Dim length5 As Length
Set length5 = limit9.Dimension

length5.Value = 50.000000

Dim limit10 As Limit
Set limit10 = pad5.SecondLimit

limit10.LimitMode = catOffsetLimit

pad5.DirectionOrientation = catRegularOrientation

part1.Update

Dim reference9 As Reference
Set reference9 = part1.CreateReferenceFromName("Selection_RSur:(Face:(Brp:(Pad.5;2);None:();Cf11:());Pad.5_ResultOUT;Z0;G3563)")

Dim sketch6 As Sketch
Set sketch6 = sketches1.Add(reference9)

Dim arrayOfVariantOfDouble6(8)
arrayOfVariantOfDouble6(0) = 0.000000
arrayOfVariantOfDouble6(1) = 0.000000
arrayOfVariantOfDouble6(2) = 325.000000
arrayOfVariantOfDouble6(3) = 1.000000
arrayOfVariantOfDouble6(4) = 0.000000
arrayOfVariantOfDouble6(5) = 0.000000
arrayOfVariantOfDouble6(6) = 0.000000
arrayOfVariantOfDouble6(7) = 1.000000
arrayOfVariantOfDouble6(8) = 0.000000
sketch6.SetAbsoluteAxisData arrayOfVariantOfDouble6

Dim factory2D6 As Factory2D
Set factory2D6 = sketch6.OpenEdition()

Dim geometricElements6 As GeometricElements
Set geometricElements6 = sketch6.GeometricElements

Dim axis2D6 As GeometricElement
Set axis2D6 = geometricElements6.Item("AbsoluteAxis")

Dim line2D19 As CATBaseDispatch
Set line2D19 = axis2D6.GetItem("HDirection")

line2D19.ReportName = 1

Dim line2D20 As CATBaseDispatch
Set line2D20 = axis2D6.GetItem("VDirection")

line2D20.ReportName = 2

Dim point2D20 As Point2D
Set point2D20 = factory2D6.CreatePoint(0.000000, 0.000000)

point2D20.ReportName = 3

Dim circle2D4 As Circle2D
Set circle2D4 = factory2D6.CreateClosedCircle(0.000000, 0.000000, 10.000000)

circle2D4.ReportName = 4

Dim point2D21 As Point2D
Set point2D21 = factory2D6.CreatePoint(0.000000, 0.000000)

point2D21.ReportName = 5

Dim circle2D5 As Circle2D
Set circle2D5 = factory2D6.CreateClosedCircle(0.000000, 0.000000, 5.000000)

circle2D5.ReportName = 6

sketch6.CloseEdition 

part1.InWorkObject = body1

part1.Update

Dim pad6 As Pad
Set pad6 = shapeFactory1.AddNewPad(sketch6, 0.0)

Dim limit11 As Limit
Set limit11 = pad6.FirstLimit

limit11.LimitMode = catOffsetLimit

Dim length6 As Length
Set length6 = limit11.Dimension

length6.Value = 37.500000

Dim limit12 As Limit
Set limit12 = pad6.SecondLimit

limit12.LimitMode = catOffsetLimit

pad6.DirectionOrientation = catRegularOrientation

part1.Update

Dim reference10 As Reference
Set reference10 = part1.CreateReferenceFromName("Selection_RSur:(Face:(Brp:(Pad.1;1);None:();Cf11:());Pad.1_ResultOUT;Z0;G3563)")

Dim sketch7 As Sketch
Set sketch7 = sketches1.Add(reference10)

Dim arrayOfVariantOfDouble7(8)
arrayOfVariantOfDouble7(0) = 0.000000
arrayOfVariantOfDouble7(1) = 0.000000
arrayOfVariantOfDouble7(2) = 0.000000
arrayOfVariantOfDouble7(3) = 1.000000
arrayOfVariantOfDouble7(4) = 0.000000
arrayOfVariantOfDouble7(5) = 0.000000
arrayOfVariantOfDouble7(6) = 0.000000
arrayOfVariantOfDouble7(7) = -1.000000
arrayOfVariantOfDouble7(8) = 0.000000
sketch7.SetAbsoluteAxisData arrayOfVariantOfDouble7

Dim factory2D7 As Factory2D
Set factory2D7 = sketch7.OpenEdition()

Dim geometricElements7 As GeometricElements
Set geometricElements7 = sketch7.GeometricElements

Dim axis2D7 As GeometricElement
Set axis2D7 = geometricElements7.Item("AbsoluteAxis")

Dim line2D21 As CATBaseDispatch
Set line2D21 = axis2D7.GetItem("HDirection")

line2D21.ReportName = 1

Dim line2D22 As CATBaseDispatch
Set line2D22 = axis2D7.GetItem("VDirection")

line2D22.ReportName = 2

Dim point2D22 As Point2D
Set point2D22 = factory2D7.CreatePoint(-45.000000, -35.000000)

point2D22.ReportName = 3

Dim point2D23 As Point2D
Set point2D23 = factory2D7.CreatePoint(-45.000000, 35.000000)

point2D23.ReportName = 4

Dim line2D23 As Line2D
Set line2D23 = factory2D7.CreateLine(-45.000000, -35.000000, -45.000000, 35.000000)

line2D23.ReportName = 5

line2D23.StartPoint = point2D22

line2D23.EndPoint = point2D23

Dim point2D24 As Point2D
Set point2D24 = factory2D7.CreatePoint(-35.000000, 35.000000)

point2D24.ReportName = 6

Dim point2D25 As Point2D
Set point2D25 = factory2D7.CreatePoint(-35.000000, 45.000000)

point2D25.ReportName = 7

Dim point2D26 As Point2D
Set point2D26 = factory2D7.CreatePoint(-45.000000, 35.000000)

point2D26.ReportName = 8

Dim circle2D6 As Circle2D
Set circle2D6 = factory2D7.CreateCircle(-35.000000, 35.000000, 10.000000, 1.570796, 3.141593)

circle2D6.ReportName = 9

Dim point2D27 As Point2D
Set point2D27 = factory2D7.CreatePoint(-35.000000, 45.000000)

point2D27.ReportName = 10

Dim point2D28 As Point2D
Set point2D28 = factory2D7.CreatePoint(35.000000, 45.000000)

point2D28.ReportName = 11

Dim line2D24 As Line2D
Set line2D24 = factory2D7.CreateLine(-35.000000, 45.000000, 35.000000, 45.000000)

line2D24.ReportName = 12

line2D24.StartPoint = point2D27

line2D24.EndPoint = point2D28

Dim point2D29 As Point2D
Set point2D29 = factory2D7.CreatePoint(35.000000, 35.000000)

point2D29.ReportName = 13

Dim point2D30 As Point2D
Set point2D30 = factory2D7.CreatePoint(45.000000, 35.000000)

point2D30.ReportName = 14

Dim point2D31 As Point2D
Set point2D31 = factory2D7.CreatePoint(35.000000, 45.000000)

point2D31.ReportName = 15

Dim circle2D7 As Circle2D
Set circle2D7 = factory2D7.CreateCircle(35.000000, 35.000000, 10.000000, 0.000000, 1.570796)

circle2D7.ReportName = 16

Dim point2D32 As Point2D
Set point2D32 = factory2D7.CreatePoint(45.000000, 35.000000)

point2D32.ReportName = 17

Dim point2D33 As Point2D
Set point2D33 = factory2D7.CreatePoint(45.000000, -35.000000)

point2D33.ReportName = 18

Dim line2D25 As Line2D
Set line2D25 = factory2D7.CreateLine(45.000000, 35.000000, 45.000000, -35.000000)

line2D25.ReportName = 19

line2D25.StartPoint = point2D32

line2D25.EndPoint = point2D33

Dim point2D34 As Point2D
Set point2D34 = factory2D7.CreatePoint(35.000000, -35.000000)

point2D34.ReportName = 20

Dim point2D35 As Point2D
Set point2D35 = factory2D7.CreatePoint(35.000000, -45.000000)

point2D35.ReportName = 21

Dim point2D36 As Point2D
Set point2D36 = factory2D7.CreatePoint(45.000000, -35.000000)

point2D36.ReportName = 22

Dim circle2D8 As Circle2D
Set circle2D8 = factory2D7.CreateCircle(35.000000, -35.000000, 10.000000, 4.712389, 0.000000)

circle2D8.ReportName = 23

Dim point2D37 As Point2D
Set point2D37 = factory2D7.CreatePoint(35.000000, -45.000000)

point2D37.ReportName = 24

Dim point2D38 As Point2D
Set point2D38 = factory2D7.CreatePoint(-35.000000, -45.000000)

point2D38.ReportName = 25

Dim line2D26 As Line2D
Set line2D26 = factory2D7.CreateLine(35.000000, -45.000000, -35.000000, -45.000000)

line2D26.ReportName = 26

line2D26.StartPoint = point2D37

line2D26.EndPoint = point2D38

Dim point2D39 As Point2D
Set point2D39 = factory2D7.CreatePoint(-35.000000, -35.000000)

point2D39.ReportName = 27

Dim point2D40 As Point2D
Set point2D40 = factory2D7.CreatePoint(-45.000000, -35.000000)

point2D40.ReportName = 28

Dim point2D41 As Point2D
Set point2D41 = factory2D7.CreatePoint(-35.000000, -45.000000)

point2D41.ReportName = 29

Dim circle2D9 As Circle2D
Set circle2D9 = factory2D7.CreateCircle(-35.000000, -35.000000, 10.000000, 3.141593, 4.712389)

circle2D9.ReportName = 30

sketch7.CloseEdition 

part1.InWorkObject = body1

part1.Update

Dim pocket1 As Pocket
Set pocket1 = shapeFactory1.AddNewPocket(sketch7, 0.0)

Dim limit13 As Limit
Set limit13 = pocket1.FirstLimit

limit13.LimitMode = catOffsetLimit

Dim length7 As Length
Set length7 = limit13.Dimension

length7.Value = 20.000000

Dim limit14 As Limit
Set limit14 = pocket1.SecondLimit

limit14.LimitMode = catOffsetLimit

pocket1.DirectionOrientation = catInverseOrientation

part1.Update

Dim reference11 As Reference
Set reference11 = part1.CreateReferenceFromName("Selection_RSur:(Face:(Brp:(Pad.3;2);None:();Cf11:());Pad.3_ResultOUT;Z0;G3563)")

Dim sketch8 As Sketch
Set sketch8 = sketches1.Add(reference11)

Dim arrayOfVariantOfDouble8(8)
arrayOfVariantOfDouble8(0) = 0.000000
arrayOfVariantOfDouble8(1) = 0.000000
arrayOfVariantOfDouble8(2) = 275.000000
arrayOfVariantOfDouble8(3) = 1.000000
arrayOfVariantOfDouble8(4) = 0.000000
arrayOfVariantOfDouble8(5) = 0.000000
arrayOfVariantOfDouble8(6) = 0.000000
arrayOfVariantOfDouble8(7) = 1.000000
arrayOfVariantOfDouble8(8) = 0.000000
sketch8.SetAbsoluteAxisData arrayOfVariantOfDouble8

Dim factory2D8 As Factory2D
Set factory2D8 = sketch8.OpenEdition()

Dim geometricElements8 As GeometricElements
Set geometricElements8 = sketch8.GeometricElements

Dim axis2D8 As GeometricElement
Set axis2D8 = geometricElements8.Item("AbsoluteAxis")

Dim line2D27 As CATBaseDispatch
Set line2D27 = axis2D8.GetItem("HDirection")

line2D27.ReportName = 1

Dim line2D28 As CATBaseDispatch
Set line2D28 = axis2D8.GetItem("VDirection")

line2D28.ReportName = 2

Dim point2D42 As Point2D
Set point2D42 = factory2D8.CreatePoint(-62.500000, -62.500000)

point2D42.ReportName = 3

Dim point2D43 As Point2D
Set point2D43 = factory2D8.CreatePoint(62.500000, -62.500000)

point2D43.ReportName = 4

Dim line2D29 As Line2D
Set line2D29 = factory2D8.CreateLine(-62.500000, -62.500000, 62.500000, -62.500000)

line2D29.ReportName = 5

line2D29.StartPoint = point2D42

line2D29.EndPoint = point2D43

Dim point2D44 As Point2D
Set point2D44 = factory2D8.CreatePoint(62.500000, -62.500000)

point2D44.ReportName = 6

Dim point2D45 As Point2D
Set point2D45 = factory2D8.CreatePoint(62.500000, 62.500000)

point2D45.ReportName = 7

Dim line2D30 As Line2D
Set line2D30 = factory2D8.CreateLine(62.500000, -62.500000, 62.500000, 62.500000)

line2D30.ReportName = 8

line2D30.StartPoint = point2D44

line2D30.EndPoint = point2D45

Dim point2D46 As Point2D
Set point2D46 = factory2D8.CreatePoint(62.500000, 62.500000)

point2D46.ReportName = 9

Dim point2D47 As Point2D
Set point2D47 = factory2D8.CreatePoint(-62.500000, 62.500000)

point2D47.ReportName = 10

Dim line2D31 As Line2D
Set line2D31 = factory2D8.CreateLine(62.500000, 62.500000, -62.500000, 62.500000)

line2D31.ReportName = 11

line2D31.StartPoint = point2D46

line2D31.EndPoint = point2D47

Dim point2D48 As Point2D
Set point2D48 = factory2D8.CreatePoint(-62.500000, 62.500000)

point2D48.ReportName = 12

Dim point2D49 As Point2D
Set point2D49 = factory2D8.CreatePoint(-62.500000, -62.500000)

point2D49.ReportName = 13

Dim line2D32 As Line2D
Set line2D32 = factory2D8.CreateLine(-62.500000, 62.500000, -62.500000, -62.500000)

line2D32.ReportName = 14

line2D32.StartPoint = point2D48

line2D32.EndPoint = point2D49

Dim point2D50 As Point2D
Set point2D50 = factory2D8.CreatePoint(-52.500000, 52.500000)

point2D50.ReportName = 15

Dim point2D51 As Point2D
Set point2D51 = factory2D8.CreatePoint(-52.500000, -52.500000)

point2D51.ReportName = 16

Dim line2D33 As Line2D
Set line2D33 = factory2D8.CreateLine(-52.500000, 52.500000, -52.500000, -52.500000)

line2D33.ReportName = 17

line2D33.StartPoint = point2D50

line2D33.EndPoint = point2D51

Dim point2D52 As Point2D
Set point2D52 = factory2D8.CreatePoint(52.500000, 52.500000)

point2D52.ReportName = 18

Dim point2D53 As Point2D
Set point2D53 = factory2D8.CreatePoint(-52.500000, 52.500000)

point2D53.ReportName = 19

Dim line2D34 As Line2D
Set line2D34 = factory2D8.CreateLine(52.500000, 52.500000, -52.500000, 52.500000)

line2D34.ReportName = 20

line2D34.StartPoint = point2D52

line2D34.EndPoint = point2D53

Dim point2D54 As Point2D
Set point2D54 = factory2D8.CreatePoint(52.500000, -52.500000)

point2D54.ReportName = 21

Dim point2D55 As Point2D
Set point2D55 = factory2D8.CreatePoint(52.500000, 52.500000)

point2D55.ReportName = 22

Dim line2D35 As Line2D
Set line2D35 = factory2D8.CreateLine(52.500000, -52.500000, 52.500000, 52.500000)

line2D35.ReportName = 23

line2D35.StartPoint = point2D54

line2D35.EndPoint = point2D55

Dim point2D56 As Point2D
Set point2D56 = factory2D8.CreatePoint(-52.500000, -52.500000)

point2D56.ReportName = 24

Dim point2D57 As Point2D
Set point2D57 = factory2D8.CreatePoint(52.500000, -52.500000)

point2D57.ReportName = 25

Dim line2D36 As Line2D
Set line2D36 = factory2D8.CreateLine(-52.500000, -52.500000, 52.500000, -52.500000)

line2D36.ReportName = 26

line2D36.StartPoint = point2D56

line2D36.EndPoint = point2D57

sketch8.CloseEdition 

part1.InWorkObject = body1

part1.Update

Dim pocket2 As Pocket
Set pocket2 = shapeFactory1.AddNewPocket(sketch8, 0.0)

Dim limit15 As Limit
Set limit15 = pocket2.FirstLimit

limit15.LimitMode = catOffsetLimit

Dim length8 As Length
Set length8 = limit15.Dimension

length8.Value = 10.000000

Dim limit16 As Limit
Set limit16 = pocket2.SecondLimit

limit16.LimitMode = catOffsetLimit

pocket2.DirectionOrientation = catInverseOrientation

part1.Update

part1.InWorkObject = body1
Dim reference12 As Reference
Set reference12 = part1.CreateReferenceFromBRepName("FSur:(Face:(Brp:(Pocket.1;2);None:();Cf11:());WithTemporaryBody;WithoutBuildError;WithInitialFeatureSupport;MonoFond;MFBRepVersion_CXR15)", pocket1)

Dim hole1 As Hole
Set hole1 = shapeFactory1.AddNewHoleFromPoint(0.000000, 0.000000, 20.000000, reference12, 100.000000)

hole1.Type = catCounterboredHole

hole1.AnchorMode = catExtremPointHoleAnchor

hole1.BottomType = catVHoleBottom

Dim limit17 As Limit
Set limit17 = hole1.BottomLimit

limit17.LimitMode = catOffsetLimit

Dim length9 As Length
Set length9 = hole1.Diameter

length9.Value = 7.000000 

Dim angle1 As Angle
Set angle1 = hole1.BottomAngle

angle1.Value = 118.000000 

Dim length10 As Length
Set length10 = hole1.HeadDiameter

length10.Value = 14.060000 

Dim length11 As Length
Set length11 = hole1.HeadDepth

length11.Value = 4.400000 

part1.Update

part1.InWorkObject = body1
Dim reference13 As Reference
Set reference13 = part1.CreateReferenceFromBRepName("FSur:(Face:(Brp:(Pad.3;0:(Brp:(Sketch.3;11)));None:();Cf11:());WithTemporaryBody;WithoutBuildError;WithInitialFeatureSupport;MonoFond;MFBRepVersion_CXR15)", pad3)

Dim hole2 As Hole
Set hole2 = shapeFactory1.AddNewHoleFromPoint(0.000000, 62.500000, 245.000000, reference13, 100.000000)

hole2.Type = catCountersunkHole

hole2.AnchorMode = catExtremPointHoleAnchor

hole2.BottomType = catFlatHoleBottom

Dim limit18 As Limit
Set limit18 = hole2.BottomLimit

limit18.LimitMode = catOffsetLimit

Dim length12 As Length
Set length12 = hole2.Diameter

length12.Value = 7.000000 

hole2.CounterSunkMode = catCSModeAngleDiameter

Dim length13 As Length
Set length13 = hole2.HeadDepth

length13.Value = 2.450000 

Dim angle2 As Angle
Set angle2 = hole2.HeadAngle

angle2.Value = 90.000000 

part1.Update

End Sub
