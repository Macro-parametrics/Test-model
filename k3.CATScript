Language = "VBSCRIPT"
Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements 

Dim shapeFactory1 As Factory
Set shapeFactory1 = part1.ShapeFactory

Dim reference1 As AnyObject
Set reference1 = originElements1.PlaneXY


Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 1.000000
arrayOfVariantOfDouble1(4) = 0.000000
arrayOfVariantOfDouble1(5) = 0.000000
arrayOfVariantOfDouble1(6) = 0.000000
arrayOfVariantOfDouble1(7) = 1.000000
arrayOfVariantOfDouble1(8) = 0.000000
sketch1.SetAbsoluteAxisData arrayOfVariantOfDouble1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(0.000000, 0.000000)

point2D1.ReportName = 3

Dim point2D2 As Point2D
Set point2D2 = factory2D1.CreatePoint(37.500000, 0.000000)

point2D2.ReportName = 4

Dim line2D3 As Line2D
Set line2D3 = factory2D1.CreateLine(0.000000, 0.000000, 37.500000, 0.000000)

line2D3.ReportName = 5

line2D3.StartPoint = point2D1

line2D3.EndPoint = point2D2

Dim point2D3 As Point2D
Set point2D3 = factory2D1.CreatePoint(37.500000, 0.000000)

point2D3.ReportName = 6

Dim point2D4 As Point2D
Set point2D4 = factory2D1.CreatePoint(37.500000, 150.000000)

point2D4.ReportName = 7

Dim line2D4 As Line2D
Set line2D4 = factory2D1.CreateLine(37.500000, 0.000000, 37.500000, 150.000000)

line2D4.ReportName = 8

line2D4.StartPoint = point2D3

line2D4.EndPoint = point2D4

Dim point2D5 As Point2D
Set point2D5 = factory2D1.CreatePoint(37.500000, 150.000000)

point2D5.ReportName = 9

Dim point2D6 As Point2D
Set point2D6 = factory2D1.CreatePoint(18.000000, 150.000000)

point2D6.ReportName = 10

Dim line2D5 As Line2D
Set line2D5 = factory2D1.CreateLine(37.500000, 150.000000, 18.000000, 150.000000)

line2D5.ReportName = 11

line2D5.StartPoint = point2D5

line2D5.EndPoint = point2D6

Dim point2D7 As Point2D
Set point2D7 = factory2D1.CreatePoint(18.000000, 150.000000)

point2D7.ReportName = 12

Dim point2D8 As Point2D
Set point2D8 = factory2D1.CreatePoint(18.000000, 180.000000)

point2D8.ReportName = 13

Dim line2D6 As Line2D
Set line2D6 = factory2D1.CreateLine(18.000000, 150.000000, 18.000000, 180.000000)

line2D6.ReportName = 14

line2D6.StartPoint = point2D7

line2D6.EndPoint = point2D8

Dim point2D9 As Point2D
Set point2D9 = factory2D1.CreatePoint(18.000000, 180.000000)

point2D9.ReportName = 15

Dim point2D10 As Point2D
Set point2D10 = factory2D1.CreatePoint(0.000000, 180.000000)

point2D10.ReportName = 16

Dim line2D7 As Line2D
Set line2D7 = factory2D1.CreateLine(18.000000, 180.000000, 0.000000, 180.000000)

line2D7.ReportName = 17

line2D7.StartPoint = point2D9

line2D7.EndPoint = point2D10

Dim point2D11 As Point2D
Set point2D11 = factory2D1.CreatePoint(0.000000, 180.000000)

point2D11.ReportName = 18

Dim point2D12 As Point2D
Set point2D12 = factory2D1.CreatePoint(0.000000, 0.000000)

point2D12.ReportName = 19

Dim line2D8 As Line2D
Set line2D8 = factory2D1.CreateLine(0.000000, 180.000000, 0.000000, 0.000000)

line2D8.ReportName = 20

line2D8.StartPoint = point2D11

line2D8.EndPoint = point2D12

Dim point2D13 As Point2D
Set point2D13 = factory2D1.CreatePoint(0.000000, 0.000000)

point2D13.ReportName = 21

Dim point2D14 As Point2D
Set point2D14 = factory2D1.CreatePoint(0.000000, 100.000000)

point2D14.ReportName = 22

Dim line2D9 As Line2D
Set line2D9 = factory2D1.CreateLine(0.000000, 0.000000, 0.000000, 100.000000)

sketch1.CenterLine = line2D9 

sketch1.CloseEdition 

part1.InWorkObject = body1

part1.Update

Dim shaft1 As Shaft
Set shaft1 = shapeFactory1.AddNewShaft(sketch1)

part1.Update

Dim reference2 As Reference
Set reference2 = part1.CreateReferenceFromName("Selection_RSur:(Face:(Brp:(Shaft.1;0:(Brp:(Sketch.1;17)));None:();Cf11:());Shaft.1_ResultOUT;Z0;G3563)")

Dim sketch2 As Sketch
Set sketch2 = sketches1.Add(reference2)

Dim arrayOfVariantOfDouble2(8)
arrayOfVariantOfDouble2(0) = 9.000000
arrayOfVariantOfDouble2(1) = 180.000000
arrayOfVariantOfDouble2(2) = 0.000000
arrayOfVariantOfDouble2(3) = 1.000000
arrayOfVariantOfDouble2(4) = 0.000000
arrayOfVariantOfDouble2(5) = 0.000000
arrayOfVariantOfDouble2(6) = 0.000000
arrayOfVariantOfDouble2(7) = 0.000000
arrayOfVariantOfDouble2(8) = -1.000000
sketch2.SetAbsoluteAxisData arrayOfVariantOfDouble2

Dim factory2D2 As Factory2D
Set factory2D2 = sketch2.OpenEdition()

Dim geometricElements2 As GeometricElements
Set geometricElements2 = sketch2.GeometricElements

Dim axis2D2 As GeometricElement
Set axis2D2 = geometricElements2.Item("AbsoluteAxis")

Dim line2D10 As CATBaseDispatch
Set line2D10 = axis2D2.GetItem("HDirection")

line2D10.ReportName = 1

Dim line2D11 As CATBaseDispatch
Set line2D11 = axis2D2.GetItem("VDirection")

line2D11.ReportName = 2

Dim point2D15 As Point2D
Set point2D15 = factory2D2.CreatePoint(-9.000000, 0.000000)

point2D15.ReportName = 3

Dim circle2D1 As Circle2D
Set circle2D1 = factory2D2.CreateClosedCircle(-9.000000, 0.000000, 10.000000)

circle2D1.ReportName = 4

sketch2.CloseEdition 

part1.InWorkObject = body1

part1.Update

Dim pocket1 As Pocket
Set pocket1 = shapeFactory1.AddNewPocket(sketch2, 0.0)

Dim limit1 As Limit
Set limit1 = pocket1.FirstLimit

limit1.LimitMode = catOffsetLimit

Dim length1 As Length
Set length1 = limit1.Dimension

length1.Value = 10.000000

Dim limit2 As Limit
Set limit2 = pocket1.SecondLimit

limit2.LimitMode = catOffsetLimit

pocket1.DirectionOrientation = catInverseOrientation

part1.Update

Dim reference3 As Reference
Set reference3 = part1.CreateReferenceFromName("")

Dim chamfer1 As Chamfer
Set chamfer1 = shapeFactory1.AddNewChamfer(reference3, catTangencyChamfer, catLengthAngleChamfer, catNoReverseChamfer, 2.500000, 45.000000)

Dim reference4 As Reference
Set reference4 = part1.CreateReferenceFromBRepName("REdge:(Edge:(Face:(Brp:(Shaft.1;0:(Brp:(Sketch.1;17)));None:();Cf11:());Face:(Brp:(Shaft.1;0:(Brp:(Sketch.1;14)));None:();Cf11:());None:(Limits1:();Limits2:());Cf11:());WithTemporaryBody;WithoutBuildError;WithSelectingFeatureSupport;MFBRepVersion_CXR14)", shaft1)

chamfer1.AddElementToChamfer reference4

chamfer1.Mode = catLengthAngleChamfer

chamfer1.Propagation = catTangencyChamfer

chamfer1.Orientation = catNoReverseChamfer

part1.Update

Dim reference5 As Reference
Set reference5 = part1.CreateReferenceFromName("")

Dim chamfer2 As Chamfer
Set chamfer2 = shapeFactory1.AddNewChamfer(reference5, catTangencyChamfer, catLengthAngleChamfer, catNoReverseChamfer, 2.500000, 45.000000)

Dim reference6 As Reference
Set reference6 = part1.CreateReferenceFromBRepName("REdge:(Edge:(Face:(Brp:(Shaft.1;0:(Brp:(Sketch.1;11)));None:();Cf11:());Face:(Brp:(Shaft.1;0:(Brp:(Sketch.1;8)));None:();Cf11:());None:(Limits1:();Limits2:());Cf11:());WithTemporaryBody;WithoutBuildError;WithSelectingFeatureSupport;MFBRepVersion_CXR14)", shaft1)

chamfer2.AddElementToChamfer reference6

chamfer2.Mode = catLengthAngleChamfer

chamfer2.Propagation = catTangencyChamfer

chamfer2.Orientation = catNoReverseChamfer

part1.Update

Dim reference7 As Reference
Set reference7 = part1.CreateReferenceFromName("")

Dim chamfer3 As Chamfer
Set chamfer3 = shapeFactory1.AddNewChamfer(reference7, catTangencyChamfer, catLengthAngleChamfer, catNoReverseChamfer, 2.500000, 45.000000)

Dim reference8 As Reference
Set reference8 = part1.CreateReferenceFromBRepName("REdge:(Edge:(Face:(Brp:(Shaft.1;0:(Brp:(Sketch.1;8)));None:();Cf11:());Face:(Brp:(Shaft.1;0:(Brp:(Sketch.1;5)));None:();Cf11:());None:(Limits1:();Limits2:());Cf11:());WithTemporaryBody;WithoutBuildError;WithSelectingFeatureSupport;MFBRepVersion_CXR14)", shaft1)

chamfer3.AddElementToChamfer reference8

chamfer3.Mode = catLengthAngleChamfer

chamfer3.Propagation = catTangencyChamfer

chamfer3.Orientation = catNoReverseChamfer

part1.Update

Dim reference9 As AnyObject
Set reference9 = originElements1.PlaneXY


Dim sketch3 As Sketch
Set sketch3 = sketches1.Add(reference9)

Dim arrayOfVariantOfDouble3(8)
arrayOfVariantOfDouble3(0) = 0.000000
arrayOfVariantOfDouble3(1) = 0.000000
arrayOfVariantOfDouble3(2) = 0.000000
arrayOfVariantOfDouble3(3) = 1.000000
arrayOfVariantOfDouble3(4) = 0.000000
arrayOfVariantOfDouble3(5) = 0.000000
arrayOfVariantOfDouble3(6) = 0.000000
arrayOfVariantOfDouble3(7) = 1.000000
arrayOfVariantOfDouble3(8) = 0.000000
sketch3.SetAbsoluteAxisData arrayOfVariantOfDouble3

Dim factory2D3 As Factory2D
Set factory2D3 = sketch3.OpenEdition()

Dim geometricElements3 As GeometricElements
Set geometricElements3 = sketch3.GeometricElements

Dim axis2D3 As GeometricElement
Set axis2D3 = geometricElements3.Item("AbsoluteAxis")

Dim line2D12 As CATBaseDispatch
Set line2D12 = axis2D3.GetItem("HDirection")

line2D12.ReportName = 1

Dim line2D13 As CATBaseDispatch
Set line2D13 = axis2D3.GetItem("VDirection")

line2D13.ReportName = 2

Dim point2D16 As Point2D
Set point2D16 = factory2D3.CreatePoint(37.500000, 129.000000)

point2D16.ReportName = 3

Dim circle2D2 As Circle2D
Set circle2D2 = factory2D3.CreateClosedCircle(37.500000, 129.000000, 2.500000)

circle2D2.ReportName = 4

Dim point2D17 As Point2D
Set point2D17 = factory2D3.CreatePoint(0.000000, 0.000000)

point2D17.ReportName = 5

Dim point2D18 As Point2D
Set point2D18 = factory2D3.CreatePoint(0.000000, 100.000000)

point2D18.ReportName = 6

Dim line2D14 As Line2D
Set line2D14 = factory2D3.CreateLine(0.000000, 0.000000, 0.000000, 100.000000)

sketch3.CenterLine = line2D14 

sketch3.CloseEdition 

part1.InWorkObject = body1

part1.Update

Dim groove1 As Groove
Set groove1 = shapeFactory1.AddNewGroove(sketch3)

part1.Update

Dim reference10 As AnyObject
Set reference10 = originElements1.PlaneXY


Dim sketch4 As Sketch
Set sketch4 = sketches1.Add(reference10)

Dim arrayOfVariantOfDouble4(8)
arrayOfVariantOfDouble4(0) = 0.000000
arrayOfVariantOfDouble4(1) = 0.000000
arrayOfVariantOfDouble4(2) = 0.000000
arrayOfVariantOfDouble4(3) = 1.000000
arrayOfVariantOfDouble4(4) = 0.000000
arrayOfVariantOfDouble4(5) = 0.000000
arrayOfVariantOfDouble4(6) = 0.000000
arrayOfVariantOfDouble4(7) = 1.000000
arrayOfVariantOfDouble4(8) = 0.000000
sketch4.SetAbsoluteAxisData arrayOfVariantOfDouble4

Dim factory2D4 As Factory2D
Set factory2D4 = sketch4.OpenEdition()

Dim geometricElements4 As GeometricElements
Set geometricElements4 = sketch4.GeometricElements

Dim axis2D4 As GeometricElement
Set axis2D4 = geometricElements4.Item("AbsoluteAxis")

Dim line2D15 As CATBaseDispatch
Set line2D15 = axis2D4.GetItem("HDirection")

line2D15.ReportName = 1

Dim line2D16 As CATBaseDispatch
Set line2D16 = axis2D4.GetItem("VDirection")

line2D16.ReportName = 2

Dim point2D19 As Point2D
Set point2D19 = factory2D4.CreatePoint(37.500000, 8.000000)

point2D19.ReportName = 3

Dim point2D20 As Point2D
Set point2D20 = factory2D4.CreatePoint(37.500000, 15.000000)

point2D20.ReportName = 4

Dim line2D17 As Line2D
Set line2D17 = factory2D4.CreateLine(37.500000, 8.000000, 37.500000, 15.000000)

line2D17.ReportName = 5

line2D17.StartPoint = point2D19

line2D17.EndPoint = point2D20

Dim point2D21 As Point2D
Set point2D21 = factory2D4.CreatePoint(37.500000, 15.000000)

point2D21.ReportName = 6

Dim point2D22 As Point2D
Set point2D22 = factory2D4.CreatePoint(33.500000, 15.000000)

point2D22.ReportName = 7

Dim line2D18 As Line2D
Set line2D18 = factory2D4.CreateLine(37.500000, 15.000000, 33.500000, 15.000000)

line2D18.ReportName = 8

line2D18.StartPoint = point2D21

line2D18.EndPoint = point2D22

Dim point2D23 As Point2D
Set point2D23 = factory2D4.CreatePoint(33.500000, 15.000000)

point2D23.ReportName = 9

Dim point2D24 As Point2D
Set point2D24 = factory2D4.CreatePoint(33.500000, 8.000000)

point2D24.ReportName = 10

Dim line2D19 As Line2D
Set line2D19 = factory2D4.CreateLine(33.500000, 15.000000, 33.500000, 8.000000)

line2D19.ReportName = 11

line2D19.StartPoint = point2D23

line2D19.EndPoint = point2D24

Dim point2D25 As Point2D
Set point2D25 = factory2D4.CreatePoint(33.500000, 8.000000)

point2D25.ReportName = 12

Dim point2D26 As Point2D
Set point2D26 = factory2D4.CreatePoint(37.500000, 8.000000)

point2D26.ReportName = 13

Dim line2D20 As Line2D
Set line2D20 = factory2D4.CreateLine(33.500000, 8.000000, 37.500000, 8.000000)

line2D20.ReportName = 14

line2D20.StartPoint = point2D25

line2D20.EndPoint = point2D26

Dim point2D27 As Point2D
Set point2D27 = factory2D4.CreatePoint(0.000000, 0.000000)

point2D27.ReportName = 15

Dim point2D28 As Point2D
Set point2D28 = factory2D4.CreatePoint(0.000000, 100.000000)

point2D28.ReportName = 16

Dim line2D21 As Line2D
Set line2D21 = factory2D4.CreateLine(0.000000, 0.000000, 0.000000, 100.000000)

sketch4.CenterLine = line2D21 

sketch4.CloseEdition 

part1.InWorkObject = body1

part1.Update

Dim groove2 As Groove
Set groove2 = shapeFactory1.AddNewGroove(sketch4)

part1.Update

Dim hybridShapeFactory1 As Factory
Set hybridShapeFactory1 = part1.HybridShapeFactory

Dim hybridShapes1 As HybridShapes
Set hybridShapes1 = body1.HybridShapes

Dim hybridShapePlaneExplicit1 As AnyObject
Set hybridShapePlaneExplicit1 = originElements1.PlaneXY

Dim reference11 As Reference

Set reference11 = part1.CreateReferenceFromObject(hybridShapePlaneExplicit1)

Dim hybridShapePlaneOffset1 As HybridShapePlaneOffset
Set hybridShapePlaneOffset1 = hybridShapeFactory1.AddNewPlaneOffset(reference11, 37.500000, False)

body1.InsertHybridShape hybridShapePlaneOffset1

part1.InWorkObject = hybridShapePlaneOffset1

part1.Update

Dim reference12 As HybridShape
Set reference12 = hybridShapes1.Item("Plane.1")

Dim sketch5 As Sketch
Set sketch5 = sketches1.Add(reference12)

Dim arrayOfVariantOfDouble5(8)
arrayOfVariantOfDouble5(0) = 0.000000
arrayOfVariantOfDouble5(1) = 0.000000
arrayOfVariantOfDouble5(2) = 37.500000
arrayOfVariantOfDouble5(3) = 1.000000
arrayOfVariantOfDouble5(4) = 0.000000
arrayOfVariantOfDouble5(5) = 0.000000
arrayOfVariantOfDouble5(6) = 0.000000
arrayOfVariantOfDouble5(7) = 1.000000
arrayOfVariantOfDouble5(8) = 0.000000
sketch5.SetAbsoluteAxisData arrayOfVariantOfDouble5

Dim factory2D5 As Factory2D
Set factory2D5 = sketch5.OpenEdition()

Dim geometricElements5 As GeometricElements
Set geometricElements5 = sketch5.GeometricElements

Dim axis2D5 As GeometricElement
Set axis2D5 = geometricElements5.Item("AbsoluteAxis")

Dim line2D22 As CATBaseDispatch
Set line2D22 = axis2D5.GetItem("HDirection")

line2D22.ReportName = 1

Dim line2D23 As CATBaseDispatch
Set line2D23 = axis2D5.GetItem("VDirection")

line2D23.ReportName = 2

Dim point2D29 As Point2D
Set point2D29 = factory2D5.CreatePoint(0.000000, 11.500000)

point2D29.ReportName = 3

Dim circle2D3 As Circle2D
Set circle2D3 = factory2D5.CreateClosedCircle(0.000000, 11.500000, 8.000000)

circle2D3.ReportName = 4

sketch5.CloseEdition 

part1.InWorkObject = body1

part1.Update

Dim pocket2 As Pocket
Set pocket2 = shapeFactory1.AddNewPocket(sketch5, 0.0)

Dim limit3 As Limit
Set limit3 = pocket2.FirstLimit

limit3.LimitMode = catOffsetLimit

Dim length2 As Length
Set length2 = limit3.Dimension

length2.Value = 10.000000

Dim limit4 As Limit
Set limit4 = pocket2.SecondLimit

limit4.LimitMode = catOffsetLimit

pocket2.DirectionOrientation = catInverseOrientation

part1.Update

End Sub
