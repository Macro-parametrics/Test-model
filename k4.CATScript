Language = "VBSCRIPT"
Sub CATMain()

Dim documents1 As Documents
Set documents1 = CATIA.Documents

Dim partDocument1 As Document
Set partDocument1 = documents1.Add("Part")

Dim part1 As Part
Set part1 = partDocument1.Part

Dim bodies1 As Bodies
Set bodies1 = part1.Bodies

Dim body1 As Body
Set body1 = bodies1.Item("PartBody")

Dim sketches1 As Sketches
Set sketches1 = body1.Sketches

Dim originElements1 As OriginElements
Set originElements1 = part1.OriginElements 

Dim shapeFactory1 As Factory
Set shapeFactory1 = part1.ShapeFactory

Dim reference1 As AnyObject
Set reference1 = originElements1.PlaneYZ


Dim sketch1 As Sketch
Set sketch1 = sketches1.Add(reference1)

Dim arrayOfVariantOfDouble1(8)
arrayOfVariantOfDouble1(0) = 0.000000
arrayOfVariantOfDouble1(1) = 0.000000
arrayOfVariantOfDouble1(2) = 0.000000
arrayOfVariantOfDouble1(3) = 0.000000
arrayOfVariantOfDouble1(4) = 1.000000
arrayOfVariantOfDouble1(5) = 0.000000
arrayOfVariantOfDouble1(6) = 0.000000
arrayOfVariantOfDouble1(7) = 0.000000
arrayOfVariantOfDouble1(8) = 1.000000
sketch1.SetAbsoluteAxisData arrayOfVariantOfDouble1

Dim factory2D1 As Factory2D
Set factory2D1 = sketch1.OpenEdition()

Dim geometricElements1 As GeometricElements
Set geometricElements1 = sketch1.GeometricElements

Dim axis2D1 As GeometricElement
Set axis2D1 = geometricElements1.Item("AbsoluteAxis")

Dim line2D1 As CATBaseDispatch
Set line2D1 = axis2D1.GetItem("HDirection")

line2D1.ReportName = 1

Dim line2D2 As CATBaseDispatch
Set line2D2 = axis2D1.GetItem("VDirection")

line2D2.ReportName = 2

Dim point2D1 As Point2D
Set point2D1 = factory2D1.CreatePoint(-50.000000, 0.000000)

point2D1.ReportName = 3

Dim point2D2 As Point2D
Set point2D2 = factory2D1.CreatePoint(50.000000, 0.000000)

point2D2.ReportName = 4

Dim line2D3 As Line2D
Set line2D3 = factory2D1.CreateLine(-50.000000, 0.000000, 50.000000, 0.000000)

line2D3.ReportName = 5

line2D3.StartPoint = point2D1

line2D3.EndPoint = point2D2

Dim point2D3 As Point2D
Set point2D3 = factory2D1.CreatePoint(50.000000, 0.000000)

point2D3.ReportName = 6

Dim point2D4 As Point2D
Set point2D4 = factory2D1.CreatePoint(50.000000, 45.000000)

point2D4.ReportName = 7

Dim line2D4 As Line2D
Set line2D4 = factory2D1.CreateLine(50.000000, 0.000000, 50.000000, 45.000000)

line2D4.ReportName = 8

line2D4.StartPoint = point2D3

line2D4.EndPoint = point2D4

Dim point2D5 As Point2D
Set point2D5 = factory2D1.CreatePoint(50.000000, 45.000000)

point2D5.ReportName = 9

Dim point2D6 As Point2D
Set point2D6 = factory2D1.CreatePoint(-50.000000, 45.000000)

point2D6.ReportName = 10

Dim line2D5 As Line2D
Set line2D5 = factory2D1.CreateLine(50.000000, 45.000000, -50.000000, 45.000000)

line2D5.ReportName = 11

line2D5.StartPoint = point2D5

line2D5.EndPoint = point2D6

Dim point2D7 As Point2D
Set point2D7 = factory2D1.CreatePoint(-50.000000, 45.000000)

point2D7.ReportName = 12

Dim point2D8 As Point2D
Set point2D8 = factory2D1.CreatePoint(-50.000000, 0.000000)

point2D8.ReportName = 13

Dim line2D6 As Line2D
Set line2D6 = factory2D1.CreateLine(-50.000000, 45.000000, -50.000000, 0.000000)

line2D6.ReportName = 14

line2D6.StartPoint = point2D7

line2D6.EndPoint = point2D8

sketch1.CloseEdition 

part1.InWorkObject = body1

part1.Update

Dim pad1 As Pad
Set pad1 = shapeFactory1.AddNewPad(sketch1, 0.0)

Dim limit1 As Limit
Set limit1 = pad1.FirstLimit

limit1.LimitMode = catOffsetLimit

Dim length1 As Length
Set length1 = limit1.Dimension

length1.Value = 150.000000

Dim limit2 As Limit
Set limit2 = pad1.SecondLimit

limit2.LimitMode = catOffsetLimit

pad1.DirectionOrientation = catRegularOrientation

part1.Update

Dim reference2 As Reference
Set reference2 = part1.CreateReferenceFromName("Selection_RSur:(Face:(Brp:(Pad.1;0:(Brp:(Sketch.1;8)));None:();Cf11:());Pad.1_ResultOUT;Z0;G3563)")

Dim sketch2 As Sketch
Set sketch2 = sketches1.Add(reference2)

Dim arrayOfVariantOfDouble2(8)
arrayOfVariantOfDouble2(0) = 75.000000
arrayOfVariantOfDouble2(1) = 50.000000
arrayOfVariantOfDouble2(2) = 0.000000
arrayOfVariantOfDouble2(3) = -1.000000
arrayOfVariantOfDouble2(4) = 0.000000
arrayOfVariantOfDouble2(5) = 0.000000
arrayOfVariantOfDouble2(6) = 0.000000
arrayOfVariantOfDouble2(7) = -0.000000
arrayOfVariantOfDouble2(8) = 1.000000
sketch2.SetAbsoluteAxisData arrayOfVariantOfDouble2

Dim factory2D2 As Factory2D
Set factory2D2 = sketch2.OpenEdition()

Dim geometricElements2 As GeometricElements
Set geometricElements2 = sketch2.GeometricElements

Dim axis2D2 As GeometricElement
Set axis2D2 = geometricElements2.Item("AbsoluteAxis")

Dim line2D7 As CATBaseDispatch
Set line2D7 = axis2D2.GetItem("HDirection")

line2D7.ReportName = 1

Dim line2D8 As CATBaseDispatch
Set line2D8 = axis2D2.GetItem("VDirection")

line2D8.ReportName = 2

Dim point2D9 As Point2D
Set point2D9 = factory2D2.CreatePoint(-72.000000, 3.000000)

point2D9.ReportName = 3

Dim point2D10 As Point2D
Set point2D10 = factory2D2.CreatePoint(72.000000, 3.000000)

point2D10.ReportName = 4

Dim line2D9 As Line2D
Set line2D9 = factory2D2.CreateLine(-72.000000, 3.000000, 72.000000, 3.000000)

line2D9.ReportName = 5

line2D9.StartPoint = point2D9

line2D9.EndPoint = point2D10

Dim point2D11 As Point2D
Set point2D11 = factory2D2.CreatePoint(72.000000, 3.000000)

point2D11.ReportName = 6

Dim point2D12 As Point2D
Set point2D12 = factory2D2.CreatePoint(72.000000, 42.000000)

point2D12.ReportName = 7

Dim line2D10 As Line2D
Set line2D10 = factory2D2.CreateLine(72.000000, 3.000000, 72.000000, 42.000000)

line2D10.ReportName = 8

line2D10.StartPoint = point2D11

line2D10.EndPoint = point2D12

Dim point2D13 As Point2D
Set point2D13 = factory2D2.CreatePoint(72.000000, 42.000000)

point2D13.ReportName = 9

Dim point2D14 As Point2D
Set point2D14 = factory2D2.CreatePoint(-72.000000, 42.000000)

point2D14.ReportName = 10

Dim line2D11 As Line2D
Set line2D11 = factory2D2.CreateLine(72.000000, 42.000000, -72.000000, 42.000000)

line2D11.ReportName = 11

line2D11.StartPoint = point2D13

line2D11.EndPoint = point2D14

Dim point2D15 As Point2D
Set point2D15 = factory2D2.CreatePoint(-72.000000, 42.000000)

point2D15.ReportName = 12

Dim point2D16 As Point2D
Set point2D16 = factory2D2.CreatePoint(-72.000000, 3.000000)

point2D16.ReportName = 13

Dim line2D12 As Line2D
Set line2D12 = factory2D2.CreateLine(-72.000000, 42.000000, -72.000000, 3.000000)

line2D12.ReportName = 14

line2D12.StartPoint = point2D15

line2D12.EndPoint = point2D16

sketch2.CloseEdition 

part1.InWorkObject = body1

part1.Update

Dim pocket1 As Pocket
Set pocket1 = shapeFactory1.AddNewPocket(sketch2, 0.0)

Dim limit3 As Limit
Set limit3 = pocket1.FirstLimit

limit3.LimitMode = catOffsetLimit

Dim length2 As Length
Set length2 = limit3.Dimension

length2.Value = 150.000000

Dim limit4 As Limit
Set limit4 = pocket1.SecondLimit

limit4.LimitMode = catOffsetLimit

pocket1.DirectionOrientation = catInverseOrientation

part1.Update

Dim reference3 As Reference
Set reference3 = part1.CreateReferenceFromName("Selection_RSur:(Face:(Brp:(Pad.1;0:(Brp:(Sketch.1;11)));None:();Cf11:());Pad.1_ResultOUT;Z0;G3563)")

Dim sketch3 As Sketch
Set sketch3 = sketches1.Add(reference3)

Dim arrayOfVariantOfDouble3(8)
arrayOfVariantOfDouble3(0) = 75.000000
arrayOfVariantOfDouble3(1) = 0.000000
arrayOfVariantOfDouble3(2) = 45.000000
arrayOfVariantOfDouble3(3) = 1.000000
arrayOfVariantOfDouble3(4) = 0.000000
arrayOfVariantOfDouble3(5) = 0.000000
arrayOfVariantOfDouble3(6) = 0.000000
arrayOfVariantOfDouble3(7) = 1.000000
arrayOfVariantOfDouble3(8) = 0.000000
sketch3.SetAbsoluteAxisData arrayOfVariantOfDouble3

Dim factory2D3 As Factory2D
Set factory2D3 = sketch3.OpenEdition()

Dim geometricElements3 As GeometricElements
Set geometricElements3 = sketch3.GeometricElements

Dim axis2D3 As GeometricElement
Set axis2D3 = geometricElements3.Item("AbsoluteAxis")

Dim line2D13 As CATBaseDispatch
Set line2D13 = axis2D3.GetItem("HDirection")

line2D13.ReportName = 1

Dim line2D14 As CATBaseDispatch
Set line2D14 = axis2D3.GetItem("VDirection")

line2D14.ReportName = 2

Dim point2D17 As Point2D
Set point2D17 = factory2D3.CreatePoint(-40.000000, -20.000000)

point2D17.ReportName = 3

Dim point2D18 As Point2D
Set point2D18 = factory2D3.CreatePoint(40.000000, -20.000000)

point2D18.ReportName = 4

Dim line2D15 As Line2D
Set line2D15 = factory2D3.CreateLine(-40.000000, -20.000000, 40.000000, -20.000000)

line2D15.ReportName = 5

line2D15.StartPoint = point2D17

line2D15.EndPoint = point2D18

Dim point2D19 As Point2D
Set point2D19 = factory2D3.CreatePoint(40.000000, -20.000000)

point2D19.ReportName = 6

Dim point2D20 As Point2D
Set point2D20 = factory2D3.CreatePoint(40.000000, 20.000000)

point2D20.ReportName = 7

Dim line2D16 As Line2D
Set line2D16 = factory2D3.CreateLine(40.000000, -20.000000, 40.000000, 20.000000)

line2D16.ReportName = 8

line2D16.StartPoint = point2D19

line2D16.EndPoint = point2D20

Dim point2D21 As Point2D
Set point2D21 = factory2D3.CreatePoint(40.000000, 20.000000)

point2D21.ReportName = 9

Dim point2D22 As Point2D
Set point2D22 = factory2D3.CreatePoint(-40.000000, 20.000000)

point2D22.ReportName = 10

Dim line2D17 As Line2D
Set line2D17 = factory2D3.CreateLine(40.000000, 20.000000, -40.000000, 20.000000)

line2D17.ReportName = 11

line2D17.StartPoint = point2D21

line2D17.EndPoint = point2D22

Dim point2D23 As Point2D
Set point2D23 = factory2D3.CreatePoint(-40.000000, 20.000000)

point2D23.ReportName = 12

Dim point2D24 As Point2D
Set point2D24 = factory2D3.CreatePoint(-40.000000, -20.000000)

point2D24.ReportName = 13

Dim line2D18 As Line2D
Set line2D18 = factory2D3.CreateLine(-40.000000, 20.000000, -40.000000, -20.000000)

line2D18.ReportName = 14

line2D18.StartPoint = point2D23

line2D18.EndPoint = point2D24

sketch3.CloseEdition 

part1.InWorkObject = body1

part1.Update

Dim pocket2 As Pocket
Set pocket2 = shapeFactory1.AddNewPocket(sketch3, 0.0)

Dim limit5 As Limit
Set limit5 = pocket2.FirstLimit

limit5.LimitMode = catOffsetLimit

Dim length3 As Length
Set length3 = limit5.Dimension

length3.Value = 25.000000

Dim limit6 As Limit
Set limit6 = pocket2.SecondLimit

limit6.LimitMode = catOffsetLimit

pocket2.DirectionOrientation = catInverseOrientation

part1.Update

Dim reference4 As Reference
Set reference4 = part1.CreateReferenceFromName("Selection_RSur:(Face:(Brp:(Pocket.1;0:(Brp:(Sketch.2;5)));None:();Cf11:());Pocket.1_ResultOUT;Z0;G3563)")

Dim sketch4 As Sketch
Set sketch4 = sketches1.Add(reference4)

Dim arrayOfVariantOfDouble4(8)
arrayOfVariantOfDouble4(0) = 75.000000
arrayOfVariantOfDouble4(1) = 0.000000
arrayOfVariantOfDouble4(2) = 3.000000
arrayOfVariantOfDouble4(3) = 1.000000
arrayOfVariantOfDouble4(4) = 0.000000
arrayOfVariantOfDouble4(5) = 0.000000
arrayOfVariantOfDouble4(6) = 0.000000
arrayOfVariantOfDouble4(7) = 1.000000
arrayOfVariantOfDouble4(8) = 0.000000
sketch4.SetAbsoluteAxisData arrayOfVariantOfDouble4

Dim factory2D4 As Factory2D
Set factory2D4 = sketch4.OpenEdition()

Dim geometricElements4 As GeometricElements
Set geometricElements4 = sketch4.GeometricElements

Dim axis2D4 As GeometricElement
Set axis2D4 = geometricElements4.Item("AbsoluteAxis")

Dim line2D19 As CATBaseDispatch
Set line2D19 = axis2D4.GetItem("HDirection")

line2D19.ReportName = 1

Dim line2D20 As CATBaseDispatch
Set line2D20 = axis2D4.GetItem("VDirection")

line2D20.ReportName = 2

Dim point2D25 As Point2D
Set point2D25 = factory2D4.CreatePoint(-20.000000, -20.000000)

point2D25.ReportName = 3

Dim point2D26 As Point2D
Set point2D26 = factory2D4.CreatePoint(20.000000, -20.000000)

point2D26.ReportName = 4

Dim line2D21 As Line2D
Set line2D21 = factory2D4.CreateLine(-20.000000, -20.000000, 20.000000, -20.000000)

line2D21.ReportName = 5

line2D21.StartPoint = point2D25

line2D21.EndPoint = point2D26

Dim point2D27 As Point2D
Set point2D27 = factory2D4.CreatePoint(20.000000, -20.000000)

point2D27.ReportName = 6

Dim point2D28 As Point2D
Set point2D28 = factory2D4.CreatePoint(20.000000, 20.000000)

point2D28.ReportName = 7

Dim line2D22 As Line2D
Set line2D22 = factory2D4.CreateLine(20.000000, -20.000000, 20.000000, 20.000000)

line2D22.ReportName = 8

line2D22.StartPoint = point2D27

line2D22.EndPoint = point2D28

Dim point2D29 As Point2D
Set point2D29 = factory2D4.CreatePoint(20.000000, 20.000000)

point2D29.ReportName = 9

Dim point2D30 As Point2D
Set point2D30 = factory2D4.CreatePoint(-20.000000, 20.000000)

point2D30.ReportName = 10

Dim line2D23 As Line2D
Set line2D23 = factory2D4.CreateLine(20.000000, 20.000000, -20.000000, 20.000000)

line2D23.ReportName = 11

line2D23.StartPoint = point2D29

line2D23.EndPoint = point2D30

Dim point2D31 As Point2D
Set point2D31 = factory2D4.CreatePoint(-20.000000, 20.000000)

point2D31.ReportName = 12

Dim point2D32 As Point2D
Set point2D32 = factory2D4.CreatePoint(-20.000000, -20.000000)

point2D32.ReportName = 13

Dim line2D24 As Line2D
Set line2D24 = factory2D4.CreateLine(-20.000000, 20.000000, -20.000000, -20.000000)

line2D24.ReportName = 14

line2D24.StartPoint = point2D31

line2D24.EndPoint = point2D32

sketch4.CloseEdition 

part1.InWorkObject = body1

part1.Update

Dim pad2 As Pad
Set pad2 = shapeFactory1.AddNewPad(sketch4, 0.0)

Dim limit7 As Limit
Set limit7 = pad2.FirstLimit

limit7.LimitMode = catOffsetLimit

Dim length4 As Length
Set length4 = limit7.Dimension

length4.Value = 38.000000

Dim limit8 As Limit
Set limit8 = pad2.SecondLimit

limit8.LimitMode = catOffsetLimit

pad2.DirectionOrientation = catRegularOrientation

part1.Update

Dim reference5 As Reference
Set reference5 = part1.CreateReferenceFromName("Selection_RSur:(Face:(Brp:(Pad.2;2);None:();Cf11:());Pad.2_ResultOUT;Z0;G3563)")

Dim sketch5 As Sketch
Set sketch5 = sketches1.Add(reference5)

Dim arrayOfVariantOfDouble5(8)
arrayOfVariantOfDouble5(0) = 75.000000
arrayOfVariantOfDouble5(1) = 0.000000
arrayOfVariantOfDouble5(2) = 41.000000
arrayOfVariantOfDouble5(3) = 1.000000
arrayOfVariantOfDouble5(4) = 0.000000
arrayOfVariantOfDouble5(5) = 0.000000
arrayOfVariantOfDouble5(6) = 0.000000
arrayOfVariantOfDouble5(7) = 1.000000
arrayOfVariantOfDouble5(8) = 0.000000
sketch5.SetAbsoluteAxisData arrayOfVariantOfDouble5

Dim factory2D5 As Factory2D
Set factory2D5 = sketch5.OpenEdition()

Dim geometricElements5 As GeometricElements
Set geometricElements5 = sketch5.GeometricElements

Dim axis2D5 As GeometricElement
Set axis2D5 = geometricElements5.Item("AbsoluteAxis")

Dim line2D25 As CATBaseDispatch
Set line2D25 = axis2D5.GetItem("HDirection")

line2D25.ReportName = 1

Dim line2D26 As CATBaseDispatch
Set line2D26 = axis2D5.GetItem("VDirection")

line2D26.ReportName = 2

Dim point2D33 As Point2D
Set point2D33 = factory2D5.CreatePoint(0.000000, 0.000000)

point2D33.ReportName = 3

Dim circle2D1 As Circle2D
Set circle2D1 = factory2D5.CreateClosedCircle(0.000000, 0.000000, 10.000000)

circle2D1.ReportName = 4

sketch5.CloseEdition 

part1.InWorkObject = body1

part1.Update

Dim pad3 As Pad
Set pad3 = shapeFactory1.AddNewPad(sketch5, 0.0)

Dim limit9 As Limit
Set limit9 = pad3.FirstLimit

limit9.LimitMode = catOffsetLimit

Dim length5 As Length
Set length5 = limit9.Dimension

length5.Value = 40.000000

Dim limit10 As Limit
Set limit10 = pad3.SecondLimit

limit10.LimitMode = catOffsetLimit

pad3.DirectionOrientation = catRegularOrientation

part1.Update

Dim reference6 As Reference
Set reference6 = part1.CreateReferenceFromName("")

Dim chamfer1 As Chamfer
Set chamfer1 = shapeFactory1.AddNewChamfer(reference6, catTangencyChamfer, catLengthAngleChamfer, catNoReverseChamfer, 3.000000, 45.000000)

Dim reference7 As Reference
Set reference7 = part1.CreateReferenceFromBRepName("REdge:(Edge:(Face:(Brp:(Pad.3;0:(Brp:(Sketch.5;4)));None:();Cf11:());Face:(Brp:(Pad.3;2);None:();Cf11:());None:(Limits1:();Limits2:());Cf11:());WithTemporaryBody;WithoutBuildError;WithSelectingFeatureSupport;MFBRepVersion_CXR14)", pad3)

chamfer1.AddElementToChamfer reference7

chamfer1.Mode = catLengthAngleChamfer

chamfer1.Propagation = catTangencyChamfer

chamfer1.Orientation = catNoReverseChamfer

part1.Update

Dim reference8 As Reference
Set reference8 = part1.CreateReferenceFromName("Selection_RSur:(Face:(Brp:(Pad.1;0:(Brp:(Sketch.1;5)));None:();Cf11:());Pad.1_ResultOUT;Z0;G3563)")

Dim sketch6 As Sketch
Set sketch6 = sketches1.Add(reference8)

Dim arrayOfVariantOfDouble6(8)
arrayOfVariantOfDouble6(0) = 18.500000
arrayOfVariantOfDouble6(1) = 25.000000
arrayOfVariantOfDouble6(2) = 0.000000
arrayOfVariantOfDouble6(3) = -1.000000
arrayOfVariantOfDouble6(4) = 0.000000
arrayOfVariantOfDouble6(5) = 0.000000
arrayOfVariantOfDouble6(6) = 0.000000
arrayOfVariantOfDouble6(7) = 1.000000
arrayOfVariantOfDouble6(8) = 0.000000
sketch6.SetAbsoluteAxisData arrayOfVariantOfDouble6

Dim factory2D6 As Factory2D
Set factory2D6 = sketch6.OpenEdition()

Dim geometricElements6 As GeometricElements
Set geometricElements6 = sketch6.GeometricElements

Dim axis2D6 As GeometricElement
Set axis2D6 = geometricElements6.Item("AbsoluteAxis")

Dim line2D27 As CATBaseDispatch
Set line2D27 = axis2D6.GetItem("HDirection")

line2D27.ReportName = 1

Dim line2D28 As CATBaseDispatch
Set line2D28 = axis2D6.GetItem("VDirection")

line2D28.ReportName = 2

Dim point2D34 As Point2D
Set point2D34 = factory2D6.CreatePoint(-7.500000, -3.000000)

point2D34.ReportName = 3

Dim point2D35 As Point2D
Set point2D35 = factory2D6.CreatePoint(7.500000, -3.000000)

point2D35.ReportName = 4

Dim line2D29 As Line2D
Set line2D29 = factory2D6.CreateLine(-7.500000, -3.000000, 7.500000, -3.000000)

line2D29.ReportName = 5

line2D29.StartPoint = point2D34

line2D29.EndPoint = point2D35

Dim point2D36 As Point2D
Set point2D36 = factory2D6.CreatePoint(7.500000, -3.000000)

point2D36.ReportName = 6

Dim point2D37 As Point2D
Set point2D37 = factory2D6.CreatePoint(7.500000, 3.000000)

point2D37.ReportName = 7

Dim line2D30 As Line2D
Set line2D30 = factory2D6.CreateLine(7.500000, -3.000000, 7.500000, 3.000000)

line2D30.ReportName = 8

line2D30.StartPoint = point2D36

line2D30.EndPoint = point2D37

Dim point2D38 As Point2D
Set point2D38 = factory2D6.CreatePoint(7.500000, 3.000000)

point2D38.ReportName = 9

Dim point2D39 As Point2D
Set point2D39 = factory2D6.CreatePoint(-7.500000, 3.000000)

point2D39.ReportName = 10

Dim line2D31 As Line2D
Set line2D31 = factory2D6.CreateLine(7.500000, 3.000000, -7.500000, 3.000000)

line2D31.ReportName = 11

line2D31.StartPoint = point2D38

line2D31.EndPoint = point2D39

Dim point2D40 As Point2D
Set point2D40 = factory2D6.CreatePoint(-7.500000, 3.000000)

point2D40.ReportName = 12

Dim point2D41 As Point2D
Set point2D41 = factory2D6.CreatePoint(-7.500000, -3.000000)

point2D41.ReportName = 13

Dim line2D32 As Line2D
Set line2D32 = factory2D6.CreateLine(-7.500000, 3.000000, -7.500000, -3.000000)

line2D32.ReportName = 14

line2D32.StartPoint = point2D40

line2D32.EndPoint = point2D41

sketch6.CloseEdition 

part1.InWorkObject = body1

part1.Update

Dim pad4 As Pad
Set pad4 = shapeFactory1.AddNewPad(sketch6, 0.0)

Dim limit11 As Limit
Set limit11 = pad4.FirstLimit

limit11.LimitMode = catOffsetLimit

Dim length6 As Length
Set length6 = limit11.Dimension

length6.Value = 38.000000

Dim limit12 As Limit
Set limit12 = pad4.SecondLimit

limit12.LimitMode = catOffsetLimit

pad4.DirectionOrientation = catRegularOrientation

part1.Update

Dim reference9 As Reference
Set reference9 = part1.CreateReferenceFromName("")

Dim reference10 As Reference
Set reference10 = part1.CreateReferenceFromName("")

Dim rectPattern1 As RectPattern
Set rectPattern1 = shapeFactory1.AddNewRectPattern(pad4, 2, 3, 25.000000, -25.000000, 1, 1, reference9, reference10, True, True, 0)

rectPattern1.FirstRectangularPatternParameters = catInstancesandSpacing

rectPattern1.SecondRectangularPatternParameters = catInstancesandSpacing

Dim reference11 As Reference
Set reference11 = originElements1.PlaneXY

rectPattern1.SetFirstDirection reference11

rectPattern1.SetSecondDirection reference11

part1.Update

End Sub
